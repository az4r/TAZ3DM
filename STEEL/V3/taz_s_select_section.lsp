(defun c:taz_s_select_section (/ taz_s_dcl_id) 

  ;; ---------------------------
  ;; Domyslne wartosci
  ;; ---------------------------
  (if (not taz_s_category) (setq taz_s_category "Dwuteowniki"))
  (if (not taz_s_family) (setq taz_s_family "HEA"))
  (if (not taz_s_type) (setq taz_s_type "100"))

  ;; ---------------------------
  ;; Zmienne tymczasowe
  ;; ---------------------------
  (setq taz_s_tmp_category taz_s_category)
  (setq taz_s_tmp_family taz_s_family)
  (setq taz_s_tmp_type taz_s_type)

  ;; ---------------------------
  ;; Wczytanie DCL
  ;; ---------------------------
  (setq taz_s_dcl_id (load_dialog "taz_s_select_section.dcl"))
  (if (not (new_dialog "taz_s_select_section" taz_s_dcl_id)) 
    (progn 
      (alert "Nie moge otworzyc DCL!")
      (exit)
    )
  )

  ;; ---------------------------
  ;; Funkcja uzupelniajaca liste rodzin
  ;; ---------------------------
  (defun taz_s_fill_family_list (taz_s_cat_val /) 
    (start_list "taz_s_fam")

    (if (= taz_s_cat_val "Dwuteowniki") 
      (progn 
        (add_list "HEA")
        (add_list "HEB")
        (add_list "IPE")
        (add_list "IPN")
      )
    )

    (if (= taz_s_cat_val "Ceowniki") 
      (progn 
        (add_list "UPE")
        (add_list "UPN")
      )
    )

    (if (= taz_s_cat_val "Katowniki") 
      (progn 
        (add_list "Katownik rownoramienny")
        (add_list "Katownik nierownoramienny")
      )
    )

    (if (= taz_s_cat_val "Rury") 
      (progn 
        (add_list "Rura kwadratowa")
        (add_list "Rura prostokatna")
        (add_list "Rura okragla")
      )
    )

    (end_list)
  )

  ;; ---------------------------
  ;; Funkcja uzupelniajaca liste typow
  ;; ---------------------------
  (defun taz_s_fill_type_list (taz_s_cat_val taz_s_fam_val /) 
    (start_list "taz_s_typ")

    ;; Dwuteowniki - HEA
    (if (and (= taz_s_cat_val "Dwuteowniki") (= taz_s_fam_val "HEA")) 
      (progn 
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "400")
        (add_list "450")
        (add_list "500")
        (add_list "550")
        (add_list "600")
        (add_list "650")
        (add_list "700")
        (add_list "800")
        (add_list "900")
        (add_list "1000")
      )
    )

    ;; Dwuteowniki - HEB
    (if (and (= taz_s_cat_val "Dwuteowniki") (= taz_s_fam_val "HEB")) 
      (progn 
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "400")
        (add_list "450")
        (add_list "500")
        (add_list "550")
        (add_list "600")
        (add_list "650")
        (add_list "700")
        (add_list "800")
        (add_list "900")
        (add_list "1000")
      )
    )

    ;; Dwuteowniki - IPE
    (if (and (= taz_s_cat_val "Dwuteowniki") (= taz_s_fam_val "IPE")) 
      (progn 
        (add_list "80")
        (add_list "100")
        (add_list "120")
        (add_list "140")
        (add_list "160")
        (add_list "180")
        (add_list "200")
        (add_list "220")
        (add_list "240")
        (add_list "270")
        (add_list "300")
        (add_list "330")
        (add_list "360")
        (add_list "400")
        (add_list "450")
        (add_list "500")
        (add_list "550")
        (add_list "600")
        (add_list "750x137")
        (add_list "750x147")
        (add_list "750x173")
        (add_list "750x196")
      )
    )

    ;; Dwuteowniki - IPN
    (if (and (= taz_s_cat_val "Dwuteowniki") (= taz_s_fam_val "IPN")) 
      (progn 
        (add_list "80")
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "380")
        (add_list "400")
        (add_list "450")
        (add_list "500")
        (add_list "550")
        (add_list "600")
      )
    )

    ;; Ceowniki – UPE
    (if (and (= taz_s_cat_val "Ceowniki") (= taz_s_fam_val "UPE")) 
      (progn 
        (add_list "80")
        (add_list "100")
        (add_list "120")
        (add_list "140")
        (add_list "160")
        (add_list "180")
        (add_list "200")
        (add_list "220")
        (add_list "240")
        (add_list "270")
        (add_list "300")
        (add_list "330")
        (add_list "360")
        (add_list "400")
      )
    )

    ;; Ceowniki – UPN
    (if (and (= taz_s_cat_val "Ceowniki") (= taz_s_fam_val "UPN")) 
      (progn 
        (add_list "50")
        (add_list "65")
        (add_list "80")
        (add_list "100")
        (add_list "120")
        (add_list "140")
        (add_list "160")
        (add_list "180")
        (add_list "200")
        (add_list "220")
        (add_list "240")
        (add_list "260")
        (add_list "280")
        (add_list "300")
        (add_list "320")
        (add_list "350")
        (add_list "380")
        (add_list "400")
      )
    )

    ;; Katowniki rownoramienne
    (if 
      (and (= taz_s_cat_val "Katowniki") 
           (= taz_s_fam_val "Katownik rownoramienny")
      )
      (progn 
        (add_list "20x3")
        (add_list "25x3")
        (add_list "25x4")
        (add_list "30x3")
        (add_list "30x4")
        (add_list "30x5")
        (add_list "35x4")
        (add_list "35x5")
        (add_list "40x4")
        (add_list "40x5")
        (add_list "45x4")
        (add_list "45x5")
        (add_list "50x5")
        (add_list "50x6")
        (add_list "50x7")
        (add_list "55x6")
        (add_list "60x5")
        (add_list "60x6")
        (add_list "60x8")
        (add_list "65x7")
        (add_list "70x6")
        (add_list "70x7")
        (add_list "70x9")
        (add_list "75x7")
        (add_list "75x8")
        (add_list "80x6")
        (add_list "80x8")
        (add_list "80x10")
        (add_list "90x7")
        (add_list "90x8")
        (add_list "90x9")
        (add_list "100x8")
        (add_list "100x10")
        (add_list "100x12")
        (add_list "100x14")
        (add_list "110x10")
        (add_list "110x12")
        (add_list "120x10")
        (add_list "120x11")
        (add_list "120x12")
        (add_list "120x13")
        (add_list "120x15")
        (add_list "130x12")
        (add_list "140x10")
        (add_list "140x13")
        (add_list "140x15")
        (add_list "150x10")
        (add_list "150x12")
        (add_list "150x14")
        (add_list "150x15")
        (add_list "150x16")
        (add_list "150x18")
        (add_list "150x20")
        (add_list "160x15")
        (add_list "160x17")
        (add_list "160x19")
        (add_list "180x16")
        (add_list "180x18")
        (add_list "180x20")
        (add_list "180x22")
        (add_list "200x16")
        (add_list "200x18")
        (add_list "200x20")
        (add_list "200x22")
        (add_list "200x24")
        (add_list "200x26")
        (add_list "200x28")
        (add_list "200x30")
        (add_list "250x18")
        (add_list "250x20")
        (add_list "250x22")
        (add_list "250x24")
        (add_list "250x26")
        (add_list "250x28")
      )
    )

    ;; Katowniki nierownoramienne
    (if 
      (and (= taz_s_cat_val "Katowniki") 
           (= taz_s_fam_val "Katownik nierownoramienny")
      )
      (progn 
        (add_list "30x20x3")
        (add_list "30x20x4")
        (add_list "40x20x3")
        (add_list "40x20x4")
        (add_list "40x25x4")
        (add_list "45x30x3")
        (add_list "45x30x4")
        (add_list "45x30x5")
        (add_list "50x30x4")
        (add_list "50x30x5")
        (add_list "50x40x4")
        (add_list "50x40x5")
        (add_list "60x30x5")
        (add_list "60x40x5")
        (add_list "60x40x6")
        (add_list "60x40x7")
        (add_list "65x50x5")
        (add_list "65x50x7")
        (add_list "65x50x9")
        (add_list "70x50x6")
        (add_list "75x50x7")
        (add_list "75x50x9")
        (add_list "75x55x5")
        (add_list "75x55x7")
        (add_list "75x55x9")
        (add_list "80x40x6")
        (add_list "80x40x8")
        (add_list "80x60x7")
        (add_list "80x65x8")
        (add_list "80x65x10")
        (add_list "90x60x6")
        (add_list "90x60x8")
        (add_list "100x50x6")
        (add_list "100x50x8")
        (add_list "100x50x10")
        (add_list "100x65x7")
        (add_list "100x65x9")
        (add_list "100x65x11")
        (add_list "100x75x7")
        (add_list "100x75x9")
        (add_list "100x75x11")
        (add_list "120x80x8")
        (add_list "120x80x10")
        (add_list "120x80x12")
        (add_list "120x80x14")
        (add_list "130x65x8")
        (add_list "130x65x10")
        (add_list "130x65x12")
        (add_list "130x90x12")
        (add_list "150x75x9")
        (add_list "150x75x11")
        (add_list "150x100x10")
        (add_list "150x100x12")
        (add_list "150x100x14")
        (add_list "160x80x12")
        (add_list "180x90x10")
        (add_list "180x90x12")
        (add_list "200x100x10")
        (add_list "200x100x12")
        (add_list "200x100x14")
        (add_list "200x100x16")
        (add_list "250x90x10")
        (add_list "250x90x12")
        (add_list "250x90x14")
        (add_list "250x90x16")
      )
    )

    ;; Rury - Rura kwadratowa (SHS)
    (if (and (= taz_s_cat_val "Rury") (= taz_s_fam_val "Rura kwadratowa")) 
      (progn 
        (add_list "38x38x2.5")
        (add_list "38x38x3")
        (add_list "38x38x3.5")
        (add_list "50x50x2.5")
        (add_list "50x50x3")
        (add_list "50x50x3.5")
        (add_list "50x50x4")
        (add_list "50x50x4.5")
        (add_list "60x60x2.5")
        (add_list "60x60x3")
        (add_list "60x60x3.5")
        (add_list "60x60x4")
        (add_list "60x60x4.5")
        (add_list "75x75x2.5")
        (add_list "75x75x3")
        (add_list "75x75x3.5")
        (add_list "75x75x4")
        (add_list "75x75x4.5")
        (add_list "75x75x5")
        (add_list "80x80x2.5")
        (add_list "80x80x3")
        (add_list "80x80x3.5")
        (add_list "80x80x4")
        (add_list "80x80x4.5")
        (add_list "80x80x5")
        (add_list "80x80x6")
        (add_list "100x100x2.5")
        (add_list "100x100x3")
        (add_list "100x100x3.5")
        (add_list "100x100x4")
        (add_list "100x100x4.5")
        (add_list "100x100x5")
        (add_list "100x100x6")
        (add_list "120x120x3")
        (add_list "120x120x3.5")
        (add_list "120x120x4")
        (add_list "120x120x4.5")
        (add_list "120x120x5")
        (add_list "120x120x6")
        (add_list "150x150x4")
        (add_list "150x150x4.5")
        (add_list "150x150x6")
        (add_list "150x150x8")
        (add_list "150x150x10")
        (add_list "175x175x4")
        (add_list "175x175x4.5")
        (add_list "175x175x6")
        (add_list "175x175x8")
        (add_list "175x175x10")
        (add_list "200x200x4.5")
        (add_list "200x200x6")
        (add_list "200x200x8")
        (add_list "200x200x10")
        (add_list "220x220x6")
        (add_list "220x220x8")
        (add_list "220x220x10")
        (add_list "250x250x4.5")
        (add_list "250x250x6")
        (add_list "250x250x8")
        (add_list "250x250x10")
        (add_list "285x285x8")
        (add_list "285x285x10")
      )
    )

    ;; Rury - Rura prostokatna (RHS)
    (if (and (= taz_s_cat_val "Rury") (= taz_s_fam_val "Rura prostokatna")) 
      (progn 
        (add_list "50x25x2.5")
        (add_list "50x25x3")
        (add_list "50x25x3.5")
        (add_list "60x40x2.5")
        (add_list "60x40x3")
        (add_list "60x40x3.5")
        (add_list "60x40x4")
        (add_list "60x40x4.5")
        (add_list "76x38x2.5")
        (add_list "76x38x3")
        (add_list "76x38x3.5")
        (add_list "76x38x4")
        (add_list "76x38x4.5")
        (add_list "80x40x2.5")
        (add_list "80x40x3")
        (add_list "80x40x3.5")
        (add_list "80x40x4")
        (add_list "80x40x4.5")
        (add_list "100x50x2.5")
        (add_list "100x50x3")
        (add_list "100x50x3.5")
        (add_list "100x50x4")
        (add_list "100x50x4.5")
        (add_list "100x50x5")
        (add_list "100x50x6")
        (add_list "120x60x3")
        (add_list "120x60x3.5")
        (add_list "120x60x4")
        (add_list "120x60x4.5")
        (add_list "120x60x5")
        (add_list "120x60x6")
        (add_list "150x100x3")
        (add_list "150x100x3.5")
        (add_list "150x100x4")
        (add_list "150x100x4.5")
        (add_list "150x100x5")
        (add_list "150x100x6")
        (add_list "160x80x3")
        (add_list "160x80x3.5")
        (add_list "160x80x4")
        (add_list "160x80x4.5")
        (add_list "160x80x5")
        (add_list "160x80x6")
        (add_list "200x100x4")
        (add_list "200x100x4.5")
        (add_list "200x100x6")
        (add_list "200x100x8")
        (add_list "200x100x10")
        (add_list "200x150x4")
        (add_list "200x150x4.5")
        (add_list "200x150x6")
        (add_list "200x150x8")
        (add_list "200x150x10")
        (add_list "250x100x4")
        (add_list "250x100x4.5")
        (add_list "250x100x6")
        (add_list "250x100x8")
        (add_list "250x100x10")
        (add_list "250x150x6")
        (add_list "250x150x8")
        (add_list "250x150x10")
        (add_list "300x140x6")
        (add_list "300x140x8")
        (add_list "300x140x10")
        (add_list "320x200x6")
        (add_list "320x200x8")
        (add_list "320x200x10")
        (add_list "340x180x6")
        (add_list "340x180x8")
        (add_list "340x180x10")
      )
    )

    ;; Rury - Rura okragla (CHS)
    (if (and (= taz_s_cat_val "Rury") (= taz_s_fam_val "Rura okragla")) 
      (progn 
        (add_list "508x12.7")
        (add_list "508x9.5")
        (add_list "457.2x12.7")
        (add_list "457.2x9.5")
        (add_list "406.4x12.7")
        (add_list "406.4x11.1")
        (add_list "406.4x9.5")
        (add_list "406.4x7.9")
        (add_list "355.6x12.7")
        (add_list "355.6x9.5")
        (add_list "355.6x7.9")
        (add_list "323.9x12.7")
        (add_list "323.9x9.5")
        (add_list "323.9x6.4")
        (add_list "317.5x15.9")
        (add_list "317.5x12.7")
        (add_list "317.5x9.5")
        (add_list "317.5x7.9")
        (add_list "317.5x6.4")
        (add_list "317.5x4.8")
        (add_list "312.8x15.9")
        (add_list "312.8x12.7")
        (add_list "312.8x9.5")
        (add_list "312.8x7.9")
        (add_list "312.8x6.4")
        (add_list "312.8x4.8")
        (add_list "311.2x15.9")
        (add_list "311.2x12.7")
        (add_list "311.2x9.5")
        (add_list "311.2x7.9")
        (add_list "311.2x6.4")
        (add_list "311.2x4.8")
        (add_list "285.8x15.9")
        (add_list "285.8x12.7")
        (add_list "285.8x9.5")
        (add_list "285.8x7.9")
        (add_list "285.8x6.4")
        (add_list "285.8x4.8")
        (add_list "273.1x12.7")
        (add_list "273.1x9.3")
        (add_list "273.1x6.4")
        (add_list "254x15.9")
        (add_list "254x12.7")
        (add_list "254x9.5")
        (add_list "254x7.9")
        (add_list "254x6.4")
        (add_list "254x4.8")
        (add_list "244.5x12.7")
        (add_list "244.5x9.5")
        (add_list "244.5x7.9")
        (add_list "244.5x6.4")
        (add_list "222.3x12.7")
        (add_list "222.3x9.5")
        (add_list "222.3x7.9")
        (add_list "222.3x6.4")
        (add_list "222.3x4.8")
        (add_list "219.1x12.7")
        (add_list "219.1x9.5")
        (add_list "219.1x8.2")
        (add_list "219.1x6.4")
        (add_list "219.1x4.8")
        (add_list "193.7x9.5")
        (add_list "193.7x8.3")
        (add_list "193.7x3.2")
        (add_list "190.5x12.7")
        (add_list "190.5x9.5")
        (add_list "190.5x7.9")
        (add_list "190.5x6.4")
        (add_list "190.5x4.8")
        (add_list "177.8x12.7")
        (add_list "177.8x9.5")
        (add_list "177.8x7.9")
        (add_list "177.8x6.4")
        (add_list "177.8x4.8")
        (add_list "177.8x3.2")
        (add_list "174.6x12.7")
        (add_list "174.6x9.5")
        (add_list "174.6x7.9")
        (add_list "174.6x6.4")
        (add_list "174.6x4.8")
        (add_list "168.3x12.7")
        (add_list "168.3x11")
        (add_list "168.3x9.5")
        (add_list "168.3x7.9")
        (add_list "168.3x7.1")
        (add_list "168.3x6.4")
        (add_list "168.3x4.8")
        (add_list "168.3x3.2")
        (add_list "155.6x12.7")
        (add_list "155.6x9.5")
        (add_list "155.6x7.9")
        (add_list "155.6x6.4")
        (add_list "155.6x4.8")
        (add_list "152.4x12.7")
        (add_list "152.4x9.5")
        (add_list "152.4x7.9")
        (add_list "152.4x7.1")
        (add_list "152.4x6.4")
        (add_list "152.4x4.8")
        (add_list "152.4x3.2")
        (add_list "141.3x9.5")
        (add_list "141.3x6.6")
        (add_list "141.3x4.8")
        (add_list "141.3x3.4")
        (add_list "139.7x12.7")
        (add_list "139.7x9.5")
        (add_list "139.7x6.6")
        (add_list "127x12.7")
        (add_list "127x9.5")
        (add_list "127x7.9")
        (add_list "127x6.6")
        (add_list "127x6.4")
        (add_list "127x4.8")
        (add_list "127x3.2")
        (add_list "114.3x8.6")
        (add_list "114.3x6")
        (add_list "114.3x4.8")
        (add_list "114.3x3.2")
        (add_list "101.6x8.6")
        (add_list "101.6x8")
        (add_list "101.6x6.4")
        (add_list "101.6x6")
        (add_list "101.6x5.7")
        (add_list "101.6x5.6")
        (add_list "101.6x4.8")
        (add_list "101.6x3.2")
        (add_list "88.9x8")
        (add_list "88.9x7.6")
        (add_list "88.9x6.4")
        (add_list "88.9x5.5")
        (add_list "88.9x5.2")
        (add_list "88.9x4.8")
        (add_list "88.9x3.2")
        (add_list "76.2x7.6")
        (add_list "76.2x6.4")
        (add_list "76.2x5.5")
        (add_list "76.2x5.2")
        (add_list "76.2x4.8")
        (add_list "76.2x3.9")
        (add_list "76.2x3.4")
        (add_list "76.2x3")
        (add_list "73x6.4")
        (add_list "73x5.2")
        (add_list "73x4.8")
        (add_list "73x3.2")
        (add_list "63.5x6.4")
        (add_list "63.5x4.8")
        (add_list "63.5x3.2")
        (add_list "60.3x6.4")
        (add_list "60.3x5.5")
        (add_list "60.3x4.8")
        (add_list "60.3x3.9")
        (add_list "60.3x3.2")
        (add_list "48.3x3.7")
        (add_list "42.2x3.6")
      )
    )

    (end_list)
  )

  ;; ---------------------------
  ;; Lista kategorii
  ;; ---------------------------
  (start_list "taz_s_cat")
  (add_list "Dwuteowniki")
  (add_list "Ceowniki")
  (add_list "Katowniki")
  (add_list "Rury")
  (end_list)

  ;; ---------------------------
  ;; Ustawienie poczatkowych wartosci
  ;; ---------------------------

  ;; Kategoria
  (if (= taz_s_tmp_category "Dwuteowniki") (set_tile "taz_s_cat" "0"))
  (if (= taz_s_tmp_category "Ceowniki") (set_tile "taz_s_cat" "1"))
  (if (= taz_s_tmp_category "Katowniki") (set_tile "taz_s_cat" "2"))
  (if (= taz_s_tmp_category "Rury") (set_tile "taz_s_cat" "3"))

  ;; Rodziny
  (taz_s_fill_family_list taz_s_tmp_category)

  ;; Dwuteowniki
  (if (= taz_s_tmp_category "Dwuteowniki") 
    (progn 
      (if (= taz_s_tmp_family "HEA") (set_tile "taz_s_fam" "0"))
      (if (= taz_s_tmp_family "HEB") (set_tile "taz_s_fam" "1"))
      (if (= taz_s_tmp_family "IPE") (set_tile "taz_s_fam" "2"))
      (if (= taz_s_tmp_family "IPN") (set_tile "taz_s_fam" "3"))
    )
  )

  ;; Ceowniki
  (if (= taz_s_tmp_category "Ceowniki") 
    (progn 
      (if (= taz_s_tmp_family "UPE") (set_tile "taz_s_fam" "0"))
      (if (= taz_s_tmp_family "UPN") (set_tile "taz_s_fam" "1"))
    )
  )

  ;; Katowniki
  (if (= taz_s_tmp_category "Katowniki") 
    (progn 
      (if (= taz_s_tmp_family "Katownik rownoramienny") (set_tile "taz_s_fam" "0"))
      (if (= taz_s_tmp_family "Katownik nierownoramienny") 
        (set_tile "taz_s_fam" "1")
      )
    )
  )

  ;; Rury
  (if (= taz_s_tmp_category "Rury") 
    (progn 
      (if (= taz_s_tmp_family "Rura kwadratowa") (set_tile "taz_s_fam" "0"))
      (if (= taz_s_tmp_family "Rura prostokatna") (set_tile "taz_s_fam" "1"))
      (if (= taz_s_tmp_family "Rura okragla") (set_tile "taz_s_fam" "2"))
    )
  )

  ;; Typy
  (taz_s_fill_type_list taz_s_tmp_category taz_s_tmp_family)
  (cond 
    ;; Dwuteowniki - HEA
    ((= taz_s_tmp_family "HEA")
     (if (= taz_s_tmp_type "100") (set_tile "taz_s_typ" "0"))
     (if (= taz_s_tmp_type "120") (set_tile "taz_s_typ" "1"))
     (if (= taz_s_tmp_type "140") (set_tile "taz_s_typ" "2"))
     (if (= taz_s_tmp_type "160") (set_tile "taz_s_typ" "3"))
     (if (= taz_s_tmp_type "180") (set_tile "taz_s_typ" "4"))
     (if (= taz_s_tmp_type "200") (set_tile "taz_s_typ" "5"))
     (if (= taz_s_tmp_type "220") (set_tile "taz_s_typ" "6"))
     (if (= taz_s_tmp_type "240") (set_tile "taz_s_typ" "7"))
     (if (= taz_s_tmp_type "260") (set_tile "taz_s_typ" "8"))
     (if (= taz_s_tmp_type "280") (set_tile "taz_s_typ" "9"))
     (if (= taz_s_tmp_type "300") (set_tile "taz_s_typ" "10"))
     (if (= taz_s_tmp_type "320") (set_tile "taz_s_typ" "11"))
     (if (= taz_s_tmp_type "340") (set_tile "taz_s_typ" "12"))
     (if (= taz_s_tmp_type "360") (set_tile "taz_s_typ" "13"))
     (if (= taz_s_tmp_type "400") (set_tile "taz_s_typ" "14"))
     (if (= taz_s_tmp_type "450") (set_tile "taz_s_typ" "15"))
     (if (= taz_s_tmp_type "500") (set_tile "taz_s_typ" "16"))
     (if (= taz_s_tmp_type "550") (set_tile "taz_s_typ" "17"))
     (if (= taz_s_tmp_type "600") (set_tile "taz_s_typ" "18"))
     (if (= taz_s_tmp_type "650") (set_tile "taz_s_typ" "19"))
     (if (= taz_s_tmp_type "700") (set_tile "taz_s_typ" "20"))
     (if (= taz_s_tmp_type "800") (set_tile "taz_s_typ" "21"))
     (if (= taz_s_tmp_type "900") (set_tile "taz_s_typ" "22"))
     (if (= taz_s_tmp_type "1000") (set_tile "taz_s_typ" "23"))
     (if 
       (and (not (= taz_s_tmp_type "100")) 
            (not (= taz_s_tmp_type "120"))
            (not (= taz_s_tmp_type "140"))
            (not (= taz_s_tmp_type "160"))
            (not (= taz_s_tmp_type "180"))
            (not (= taz_s_tmp_type "200"))
            (not (= taz_s_tmp_type "220"))
            (not (= taz_s_tmp_type "240"))
            (not (= taz_s_tmp_type "260"))
            (not (= taz_s_tmp_type "280"))
            (not (= taz_s_tmp_type "300"))
            (not (= taz_s_tmp_type "320"))
            (not (= taz_s_tmp_type "340"))
            (not (= taz_s_tmp_type "360"))
            (not (= taz_s_tmp_type "400"))
            (not (= taz_s_tmp_type "450"))
            (not (= taz_s_tmp_type "500"))
            (not (= taz_s_tmp_type "550"))
            (not (= taz_s_tmp_type "600"))
            (not (= taz_s_tmp_type "650"))
            (not (= taz_s_tmp_type "700"))
            (not (= taz_s_tmp_type "800"))
            (not (= taz_s_tmp_type "900"))
            (not (= taz_s_tmp_type "1000"))
       )
       (progn (setq taz_s_tmp_type "100") (set_tile "taz_s_typ" "0"))
     )
    )

    ;; Dwuteowniki - HEB
    ((= taz_s_tmp_family "HEB")
     (if (= taz_s_tmp_type "100") (set_tile "taz_s_typ" "0"))
     (if (= taz_s_tmp_type "120") (set_tile "taz_s_typ" "1"))
     (if (= taz_s_tmp_type "140") (set_tile "taz_s_typ" "2"))
     (if (= taz_s_tmp_type "160") (set_tile "taz_s_typ" "3"))
     (if (= taz_s_tmp_type "180") (set_tile "taz_s_typ" "4"))
     (if (= taz_s_tmp_type "200") (set_tile "taz_s_typ" "5"))
     (if (= taz_s_tmp_type "220") (set_tile "taz_s_typ" "6"))
     (if (= taz_s_tmp_type "240") (set_tile "taz_s_typ" "7"))
     (if (= taz_s_tmp_type "260") (set_tile "taz_s_typ" "8"))
     (if (= taz_s_tmp_type "280") (set_tile "taz_s_typ" "9"))
     (if (= taz_s_tmp_type "300") (set_tile "taz_s_typ" "10"))
     (if (= taz_s_tmp_type "320") (set_tile "taz_s_typ" "11"))
     (if (= taz_s_tmp_type "340") (set_tile "taz_s_typ" "12"))
     (if (= taz_s_tmp_type "360") (set_tile "taz_s_typ" "13"))
     (if (= taz_s_tmp_type "400") (set_tile "taz_s_typ" "14"))
     (if (= taz_s_tmp_type "450") (set_tile "taz_s_typ" "15"))
     (if (= taz_s_tmp_type "500") (set_tile "taz_s_typ" "16"))
     (if (= taz_s_tmp_type "550") (set_tile "taz_s_typ" "17"))
     (if (= taz_s_tmp_type "600") (set_tile "taz_s_typ" "18"))
     (if (= taz_s_tmp_type "650") (set_tile "taz_s_typ" "19"))
     (if (= taz_s_tmp_type "700") (set_tile "taz_s_typ" "20"))
     (if (= taz_s_tmp_type "800") (set_tile "taz_s_typ" "21"))
     (if (= taz_s_tmp_type "900") (set_tile "taz_s_typ" "22"))
     (if (= taz_s_tmp_type "1000") (set_tile "taz_s_typ" "23"))
     (if 
       (and (not (= taz_s_tmp_type "100")) 
            (not (= taz_s_tmp_type "120"))
            (not (= taz_s_tmp_type "140"))
            (not (= taz_s_tmp_type "160"))
            (not (= taz_s_tmp_type "180"))
            (not (= taz_s_tmp_type "200"))
            (not (= taz_s_tmp_type "220"))
            (not (= taz_s_tmp_type "240"))
            (not (= taz_s_tmp_type "260"))
            (not (= taz_s_tmp_type "280"))
            (not (= taz_s_tmp_type "300"))
            (not (= taz_s_tmp_type "320"))
            (not (= taz_s_tmp_type "340"))
            (not (= taz_s_tmp_type "360"))
            (not (= taz_s_tmp_type "400"))
            (not (= taz_s_tmp_type "450"))
            (not (= taz_s_tmp_type "500"))
            (not (= taz_s_tmp_type "550"))
            (not (= taz_s_tmp_type "600"))
            (not (= taz_s_tmp_type "650"))
            (not (= taz_s_tmp_type "700"))
            (not (= taz_s_tmp_type "800"))
            (not (= taz_s_tmp_type "900"))
            (not (= taz_s_tmp_type "1000"))
       )
       (progn (setq taz_s_tmp_type "100") (set_tile "taz_s_typ" "0"))
     )
    )

    ;; Dwuteowniki - IPE
    ((= taz_s_tmp_family "IPE")
     (if (= taz_s_tmp_type "80") (set_tile "taz_s_typ" "0"))
     (if (= taz_s_tmp_type "100") (set_tile "taz_s_typ" "1"))
     (if (= taz_s_tmp_type "120") (set_tile "taz_s_typ" "2"))
     (if (= taz_s_tmp_type "140") (set_tile "taz_s_typ" "3"))
     (if (= taz_s_tmp_type "160") (set_tile "taz_s_typ" "4"))
     (if (= taz_s_tmp_type "180") (set_tile "taz_s_typ" "5"))
     (if (= taz_s_tmp_type "200") (set_tile "taz_s_typ" "6"))
     (if (= taz_s_tmp_type "220") (set_tile "taz_s_typ" "7"))
     (if (= taz_s_tmp_type "240") (set_tile "taz_s_typ" "8"))
     (if (= taz_s_tmp_type "270") (set_tile "taz_s_typ" "9"))
     (if (= taz_s_tmp_type "300") (set_tile "taz_s_typ" "10"))
     (if (= taz_s_tmp_type "330") (set_tile "taz_s_typ" "11"))
     (if (= taz_s_tmp_type "360") (set_tile "taz_s_typ" "12"))
     (if (= taz_s_tmp_type "400") (set_tile "taz_s_typ" "13"))
     (if (= taz_s_tmp_type "450") (set_tile "taz_s_typ" "14"))
     (if (= taz_s_tmp_type "500") (set_tile "taz_s_typ" "15"))
     (if (= taz_s_tmp_type "550") (set_tile "taz_s_typ" "16"))
     (if (= taz_s_tmp_type "600") (set_tile "taz_s_typ" "17"))
     (if (= taz_s_tmp_type "750x137") (set_tile "taz_s_typ" "18"))
     (if (= taz_s_tmp_type "750x147") (set_tile "taz_s_typ" "19"))
     (if (= taz_s_tmp_type "750x173") (set_tile "taz_s_typ" "20"))
     (if (= taz_s_tmp_type "750x196") (set_tile "taz_s_typ" "21"))
     (if 
       (and (not (= taz_s_tmp_type "80")) 
            (not (= taz_s_tmp_type "100"))
            (not (= taz_s_tmp_type "120"))
            (not (= taz_s_tmp_type "140"))
            (not (= taz_s_tmp_type "160"))
            (not (= taz_s_tmp_type "180"))
            (not (= taz_s_tmp_type "200"))
            (not (= taz_s_tmp_type "220"))
            (not (= taz_s_tmp_type "240"))
            (not (= taz_s_tmp_type "270"))
            (not (= taz_s_tmp_type "300"))
            (not (= taz_s_tmp_type "330"))
            (not (= taz_s_tmp_type "360"))
            (not (= taz_s_tmp_type "400"))
            (not (= taz_s_tmp_type "450"))
            (not (= taz_s_tmp_type "500"))
            (not (= taz_s_tmp_type "550"))
            (not (= taz_s_tmp_type "600"))
            (not (= taz_s_tmp_type "750x137"))
            (not (= taz_s_tmp_type "750x147"))
            (not (= taz_s_tmp_type "750x173"))
            (not (= taz_s_tmp_type "750x196"))
       )
       (progn (setq taz_s_tmp_type "80") (set_tile "taz_s_typ" "0"))
     )
    )

    ;; Dwuteowniki - IPN
    ((= taz_s_tmp_family "IPN")
     (if (= taz_s_tmp_type "80") (set_tile "taz_s_typ" "0"))
     (if (= taz_s_tmp_type "100") (set_tile "taz_s_typ" "1"))
     (if (= taz_s_tmp_type "120") (set_tile "taz_s_typ" "2"))
     (if (= taz_s_tmp_type "140") (set_tile "taz_s_typ" "3"))
     (if (= taz_s_tmp_type "160") (set_tile "taz_s_typ" "4"))
     (if (= taz_s_tmp_type "180") (set_tile "taz_s_typ" "5"))
     (if (= taz_s_tmp_type "200") (set_tile "taz_s_typ" "6"))
     (if (= taz_s_tmp_type "220") (set_tile "taz_s_typ" "7"))
     (if (= taz_s_tmp_type "240") (set_tile "taz_s_typ" "8"))
     (if (= taz_s_tmp_type "260") (set_tile "taz_s_typ" "9"))
     (if (= taz_s_tmp_type "280") (set_tile "taz_s_typ" "10"))
     (if (= taz_s_tmp_type "300") (set_tile "taz_s_typ" "11"))
     (if (= taz_s_tmp_type "320") (set_tile "taz_s_typ" "12"))
     (if (= taz_s_tmp_type "340") (set_tile "taz_s_typ" "13"))
     (if (= taz_s_tmp_type "360") (set_tile "taz_s_typ" "14"))
     (if (= taz_s_tmp_type "380") (set_tile "taz_s_typ" "15"))
     (if (= taz_s_tmp_type "400") (set_tile "taz_s_typ" "16"))
     (if (= taz_s_tmp_type "450") (set_tile "taz_s_typ" "17"))
     (if (= taz_s_tmp_type "500") (set_tile "taz_s_typ" "18"))
     (if (= taz_s_tmp_type "550") (set_tile "taz_s_typ" "19"))
     (if (= taz_s_tmp_type "600") (set_tile "taz_s_typ" "20"))
     (if 
       (and (not (= taz_s_tmp_type "80")) 
            (not (= taz_s_tmp_type "100"))
            (not (= taz_s_tmp_type "120"))
            (not (= taz_s_tmp_type "120"))
            (not (= taz_s_tmp_type "140"))
            (not (= taz_s_tmp_type "160"))
            (not (= taz_s_tmp_type "180"))
            (not (= taz_s_tmp_type "200"))
            (not (= taz_s_tmp_type "220"))
            (not (= taz_s_tmp_type "240"))
            (not (= taz_s_tmp_type "260"))
            (not (= taz_s_tmp_type "280"))
            (not (= taz_s_tmp_type "300"))
            (not (= taz_s_tmp_type "320"))
            (not (= taz_s_tmp_type "340"))
            (not (= taz_s_tmp_type "360"))
            (not (= taz_s_tmp_type "380"))
            (not (= taz_s_tmp_type "400"))
            (not (= taz_s_tmp_type "450"))
            (not (= taz_s_tmp_type "500"))
            (not (= taz_s_tmp_type "550"))
            (not (= taz_s_tmp_type "600"))
       )
       (progn (setq taz_s_tmp_type "80") (set_tile "taz_s_typ" "0"))
     )
    )

    ;; Ceowniki - UPE
    ((= taz_s_tmp_family "UPE")
     (if (= taz_s_tmp_type "80") (set_tile "taz_s_typ" "0"))
     (if (= taz_s_tmp_type "100") (set_tile "taz_s_typ" "1"))
     (if (= taz_s_tmp_type "120") (set_tile "taz_s_typ" "2"))
     (if (= taz_s_tmp_type "140") (set_tile "taz_s_typ" "3"))
     (if (= taz_s_tmp_type "160") (set_tile "taz_s_typ" "4"))
     (if (= taz_s_tmp_type "180") (set_tile "taz_s_typ" "5"))
     (if (= taz_s_tmp_type "200") (set_tile "taz_s_typ" "6"))
     (if (= taz_s_tmp_type "220") (set_tile "taz_s_typ" "7"))
     (if (= taz_s_tmp_type "240") (set_tile "taz_s_typ" "8"))
     (if (= taz_s_tmp_type "270") (set_tile "taz_s_typ" "9"))
     (if (= taz_s_tmp_type "300") (set_tile "taz_s_typ" "10"))
     (if (= taz_s_tmp_type "330") (set_tile "taz_s_typ" "11"))
     (if (= taz_s_tmp_type "360") (set_tile "taz_s_typ" "12"))
     (if (= taz_s_tmp_type "400") (set_tile "taz_s_typ" "13"))
     (if 
       (and (not (= taz_s_tmp_type "80")) 
            (not (= taz_s_tmp_type "100"))
            (not (= taz_s_tmp_type "120"))
            (not (= taz_s_tmp_type "140"))
            (not (= taz_s_tmp_type "160"))
            (not (= taz_s_tmp_type "180"))
            (not (= taz_s_tmp_type "200"))
            (not (= taz_s_tmp_type "220"))
            (not (= taz_s_tmp_type "240"))
            (not (= taz_s_tmp_type "270"))
            (not (= taz_s_tmp_type "300"))
            (not (= taz_s_tmp_type "330"))
            (not (= taz_s_tmp_type "360"))
            (not (= taz_s_tmp_type "400"))
       )
       (progn (setq taz_s_tmp_type "80") (set_tile "taz_s_typ" "0"))
     )
    )

    ;; Ceowniki - UPN
    ((= taz_s_tmp_family "UPN")
     (if (= taz_s_tmp_type "50") (set_tile "taz_s_typ" "0"))
     (if (= taz_s_tmp_type "65") (set_tile "taz_s_typ" "1"))
     (if (= taz_s_tmp_type "80") (set_tile "taz_s_typ" "2"))
     (if (= taz_s_tmp_type "100") (set_tile "taz_s_typ" "3"))
     (if (= taz_s_tmp_type "120") (set_tile "taz_s_typ" "4"))
     (if (= taz_s_tmp_type "140") (set_tile "taz_s_typ" "5"))
     (if (= taz_s_tmp_type "160") (set_tile "taz_s_typ" "6"))
     (if (= taz_s_tmp_type "180") (set_tile "taz_s_typ" "7"))
     (if (= taz_s_tmp_type "200") (set_tile "taz_s_typ" "8"))
     (if (= taz_s_tmp_type "220") (set_tile "taz_s_typ" "9"))
     (if (= taz_s_tmp_type "240") (set_tile "taz_s_typ" "10"))
     (if (= taz_s_tmp_type "260") (set_tile "taz_s_typ" "11"))
     (if (= taz_s_tmp_type "280") (set_tile "taz_s_typ" "12"))
     (if (= taz_s_tmp_type "300") (set_tile "taz_s_typ" "13"))
     (if (= taz_s_tmp_type "320") (set_tile "taz_s_typ" "14"))
     (if (= taz_s_tmp_type "350") (set_tile "taz_s_typ" "15"))
     (if (= taz_s_tmp_type "380") (set_tile "taz_s_typ" "16"))
     (if (= taz_s_tmp_type "400") (set_tile "taz_s_typ" "17"))
     (if 
       (and (not (= taz_s_tmp_type "50")) 
            (not (= taz_s_tmp_type "65"))
            (not (= taz_s_tmp_type "80"))
            (not (= taz_s_tmp_type "100"))
            (not (= taz_s_tmp_type "120"))
            (not (= taz_s_tmp_type "140"))
            (not (= taz_s_tmp_type "160"))
            (not (= taz_s_tmp_type "180"))
            (not (= taz_s_tmp_type "200"))
            (not (= taz_s_tmp_type "220"))
            (not (= taz_s_tmp_type "240"))
            (not (= taz_s_tmp_type "260"))
            (not (= taz_s_tmp_type "280"))
            (not (= taz_s_tmp_type "300"))
            (not (= taz_s_tmp_type "320"))
            (not (= taz_s_tmp_type "350"))
            (not (= taz_s_tmp_type "380"))
            (not (= taz_s_tmp_type "400"))
       )
       (progn (setq taz_s_tmp_type "50") (set_tile "taz_s_typ" "0"))
     )
    )

    ;; Katowniki rownoramienne
    ((= taz_s_tmp_family "Katownik rownoramienny")
     (if (= taz_s_tmp_type "20x3") (set_tile "taz_s_typ" "0"))
     (if (= taz_s_tmp_type "25x3") (set_tile "taz_s_typ" "1"))
     (if (= taz_s_tmp_type "25x4") (set_tile "taz_s_typ" "2"))
     (if (= taz_s_tmp_type "30x3") (set_tile "taz_s_typ" "3"))
     (if (= taz_s_tmp_type "30x4") (set_tile "taz_s_typ" "4"))
     (if (= taz_s_tmp_type "30x5") (set_tile "taz_s_typ" "5"))
     (if (= taz_s_tmp_type "35x4") (set_tile "taz_s_typ" "6"))
     (if (= taz_s_tmp_type "35x5") (set_tile "taz_s_typ" "7"))
     (if (= taz_s_tmp_type "40x4") (set_tile "taz_s_typ" "8"))
     (if (= taz_s_tmp_type "40x5") (set_tile "taz_s_typ" "9"))
     (if (= taz_s_tmp_type "45x4") (set_tile "taz_s_typ" "10"))
     (if (= taz_s_tmp_type "45x5") (set_tile "taz_s_typ" "11"))
     (if (= taz_s_tmp_type "50x5") (set_tile "taz_s_typ" "12"))
     (if (= taz_s_tmp_type "50x6") (set_tile "taz_s_typ" "13"))
     (if (= taz_s_tmp_type "50x7") (set_tile "taz_s_typ" "14"))
     (if (= taz_s_tmp_type "55x6") (set_tile "taz_s_typ" "15"))
     (if (= taz_s_tmp_type "60x5") (set_tile "taz_s_typ" "16"))
     (if (= taz_s_tmp_type "60x6") (set_tile "taz_s_typ" "17"))
     (if (= taz_s_tmp_type "60x8") (set_tile "taz_s_typ" "18"))
     (if (= taz_s_tmp_type "65x7") (set_tile "taz_s_typ" "19"))
     (if (= taz_s_tmp_type "70x6") (set_tile "taz_s_typ" "20"))
     (if (= taz_s_tmp_type "70x7") (set_tile "taz_s_typ" "21"))
     (if (= taz_s_tmp_type "70x9") (set_tile "taz_s_typ" "22"))
     (if (= taz_s_tmp_type "75x7") (set_tile "taz_s_typ" "23"))
     (if (= taz_s_tmp_type "75x8") (set_tile "taz_s_typ" "24"))
     (if (= taz_s_tmp_type "80x6") (set_tile "taz_s_typ" "25"))
     (if (= taz_s_tmp_type "80x8") (set_tile "taz_s_typ" "26"))
     (if (= taz_s_tmp_type "80x10") (set_tile "taz_s_typ" "27"))
     (if (= taz_s_tmp_type "90x7") (set_tile "taz_s_typ" "28"))
     (if (= taz_s_tmp_type "90x8") (set_tile "taz_s_typ" "29"))
     (if (= taz_s_tmp_type "90x9") (set_tile "taz_s_typ" "30"))
     (if (= taz_s_tmp_type "100x8") (set_tile "taz_s_typ" "31"))
     (if (= taz_s_tmp_type "100x10") (set_tile "taz_s_typ" "32"))
     (if (= taz_s_tmp_type "100x12") (set_tile "taz_s_typ" "33"))
     (if (= taz_s_tmp_type "100x14") (set_tile "taz_s_typ" "34"))
     (if (= taz_s_tmp_type "110x10") (set_tile "taz_s_typ" "35"))
     (if (= taz_s_tmp_type "110x12") (set_tile "taz_s_typ" "36"))
     (if (= taz_s_tmp_type "120x10") (set_tile "taz_s_typ" "37"))
     (if (= taz_s_tmp_type "120x11") (set_tile "taz_s_typ" "38"))
     (if (= taz_s_tmp_type "120x12") (set_tile "taz_s_typ" "39"))
     (if (= taz_s_tmp_type "120x13") (set_tile "taz_s_typ" "40"))
     (if (= taz_s_tmp_type "120x15") (set_tile "taz_s_typ" "41"))
     (if (= taz_s_tmp_type "130x12") (set_tile "taz_s_typ" "42"))
     (if (= taz_s_tmp_type "140x10") (set_tile "taz_s_typ" "43"))
     (if (= taz_s_tmp_type "140x13") (set_tile "taz_s_typ" "44"))
     (if (= taz_s_tmp_type "140x15") (set_tile "taz_s_typ" "45"))
     (if (= taz_s_tmp_type "150x10") (set_tile "taz_s_typ" "46"))
     (if (= taz_s_tmp_type "150x12") (set_tile "taz_s_typ" "47"))
     (if (= taz_s_tmp_type "150x14") (set_tile "taz_s_typ" "48"))
     (if (= taz_s_tmp_type "150x15") (set_tile "taz_s_typ" "49"))
     (if (= taz_s_tmp_type "150x16") (set_tile "taz_s_typ" "50"))
     (if (= taz_s_tmp_type "150x18") (set_tile "taz_s_typ" "51"))
     (if (= taz_s_tmp_type "150x20") (set_tile "taz_s_typ" "52"))
     (if (= taz_s_tmp_type "160x15") (set_tile "taz_s_typ" "53"))
     (if (= taz_s_tmp_type "160x17") (set_tile "taz_s_typ" "54"))
     (if (= taz_s_tmp_type "160x19") (set_tile "taz_s_typ" "55"))
     (if (= taz_s_tmp_type "180x16") (set_tile "taz_s_typ" "56"))
     (if (= taz_s_tmp_type "180x18") (set_tile "taz_s_typ" "57"))
     (if (= taz_s_tmp_type "180x20") (set_tile "taz_s_typ" "58"))
     (if (= taz_s_tmp_type "180x22") (set_tile "taz_s_typ" "59"))
     (if (= taz_s_tmp_type "200x16") (set_tile "taz_s_typ" "60"))
     (if (= taz_s_tmp_type "200x18") (set_tile "taz_s_typ" "61"))
     (if (= taz_s_tmp_type "200x20") (set_tile "taz_s_typ" "62"))
     (if (= taz_s_tmp_type "200x22") (set_tile "taz_s_typ" "63"))
     (if (= taz_s_tmp_type "200x24") (set_tile "taz_s_typ" "64"))
     (if (= taz_s_tmp_type "200x26") (set_tile "taz_s_typ" "65"))
     (if (= taz_s_tmp_type "200x28") (set_tile "taz_s_typ" "66"))
     (if (= taz_s_tmp_type "200x30") (set_tile "taz_s_typ" "67"))
     (if (= taz_s_tmp_type "250x18") (set_tile "taz_s_typ" "68"))
     (if (= taz_s_tmp_type "250x20") (set_tile "taz_s_typ" "69"))
     (if (= taz_s_tmp_type "250x22") (set_tile "taz_s_typ" "70"))
     (if (= taz_s_tmp_type "250x24") (set_tile "taz_s_typ" "71"))
     (if (= taz_s_tmp_type "250x26") (set_tile "taz_s_typ" "72"))
     (if (= taz_s_tmp_type "250x28") (set_tile "taz_s_typ" "73"))
     (if 
       (and (not (= taz_s_tmp_type "20x3")) 
            (not (= taz_s_tmp_type "25x3"))
            (not (= taz_s_tmp_type "25x4"))
            (not (= taz_s_tmp_type "30x3"))
            (not (= taz_s_tmp_type "30x4"))
            (not (= taz_s_tmp_type "30x5"))
            (not (= taz_s_tmp_type "35x4"))
            (not (= taz_s_tmp_type "35x5"))
            (not (= taz_s_tmp_type "40x4"))
            (not (= taz_s_tmp_type "40x5"))
            (not (= taz_s_tmp_type "45x4"))
            (not (= taz_s_tmp_type "45x5"))
            (not (= taz_s_tmp_type "50x5"))
            (not (= taz_s_tmp_type "50x6"))
            (not (= taz_s_tmp_type "50x7"))
            (not (= taz_s_tmp_type "55x6"))
            (not (= taz_s_tmp_type "60x5"))
            (not (= taz_s_tmp_type "60x6"))
            (not (= taz_s_tmp_type "60x8"))
            (not (= taz_s_tmp_type "65x7"))
            (not (= taz_s_tmp_type "70x6"))
            (not (= taz_s_tmp_type "70x7"))
            (not (= taz_s_tmp_type "70x9"))
            (not (= taz_s_tmp_type "75x7"))
            (not (= taz_s_tmp_type "75x8"))
            (not (= taz_s_tmp_type "80x6"))
            (not (= taz_s_tmp_type "80x8"))
            (not (= taz_s_tmp_type "80x10"))
            (not (= taz_s_tmp_type "90x7"))
            (not (= taz_s_tmp_type "90x8"))
            (not (= taz_s_tmp_type "90x9"))
            (not (= taz_s_tmp_type "100x8"))
            (not (= taz_s_tmp_type "100x10"))
            (not (= taz_s_tmp_type "100x12"))
            (not (= taz_s_tmp_type "100x14"))
            (not (= taz_s_tmp_type "110x10"))
            (not (= taz_s_tmp_type "110x12"))
            (not (= taz_s_tmp_type "120x10"))
            (not (= taz_s_tmp_type "120x11"))
            (not (= taz_s_tmp_type "120x12"))
            (not (= taz_s_tmp_type "120x13"))
            (not (= taz_s_tmp_type "120x15"))
            (not (= taz_s_tmp_type "130x12"))
            (not (= taz_s_tmp_type "140x10"))
            (not (= taz_s_tmp_type "140x13"))
            (not (= taz_s_tmp_type "140x15"))
            (not (= taz_s_tmp_type "150x10"))
            (not (= taz_s_tmp_type "150x12"))
            (not (= taz_s_tmp_type "150x14"))
            (not (= taz_s_tmp_type "150x15"))
            (not (= taz_s_tmp_type "150x16"))
            (not (= taz_s_tmp_type "150x18"))
            (not (= taz_s_tmp_type "150x20"))
            (not (= taz_s_tmp_type "160x15"))
            (not (= taz_s_tmp_type "160x17"))
            (not (= taz_s_tmp_type "160x19"))
            (not (= taz_s_tmp_type "180x16"))
            (not (= taz_s_tmp_type "180x18"))
            (not (= taz_s_tmp_type "180x20"))
            (not (= taz_s_tmp_type "180x22"))
            (not (= taz_s_tmp_type "200x16"))
            (not (= taz_s_tmp_type "200x18"))
            (not (= taz_s_tmp_type "200x20"))
            (not (= taz_s_tmp_type "200x22"))
            (not (= taz_s_tmp_type "200x24"))
            (not (= taz_s_tmp_type "200x26"))
            (not (= taz_s_tmp_type "200x28"))
            (not (= taz_s_tmp_type "200x30"))
            (not (= taz_s_tmp_type "250x18"))
            (not (= taz_s_tmp_type "250x20"))
            (not (= taz_s_tmp_type "250x22"))
            (not (= taz_s_tmp_type "250x24"))
            (not (= taz_s_tmp_type "250x26"))
            (not (= taz_s_tmp_type "250x28"))
       )
       (progn (setq taz_s_tmp_type "20x3") (set_tile "taz_s_typ" "0"))
     )
    )

    ;; Katowniki nierownoramienne
    ((= taz_s_tmp_family "Katownik nierownoramienny")
     (if (= taz_s_tmp_type "30x20x3") (set_tile "taz_s_typ" "0"))
     (if (= taz_s_tmp_type "30x20x4") (set_tile "taz_s_typ" "1"))
     (if (= taz_s_tmp_type "40x20x3") (set_tile "taz_s_typ" "2"))
     (if (= taz_s_tmp_type "40x20x4") (set_tile "taz_s_typ" "3"))
     (if (= taz_s_tmp_type "40x25x4") (set_tile "taz_s_typ" "4"))
     (if (= taz_s_tmp_type "45x30x3") (set_tile "taz_s_typ" "5"))
     (if (= taz_s_tmp_type "45x30x4") (set_tile "taz_s_typ" "6"))
     (if (= taz_s_tmp_type "45x30x5") (set_tile "taz_s_typ" "7"))
     (if (= taz_s_tmp_type "50x30x4") (set_tile "taz_s_typ" "8"))
     (if (= taz_s_tmp_type "50x30x5") (set_tile "taz_s_typ" "9"))
     (if (= taz_s_tmp_type "50x40x4") (set_tile "taz_s_typ" "10"))
     (if (= taz_s_tmp_type "50x40x5") (set_tile "taz_s_typ" "11"))
     (if (= taz_s_tmp_type "60x30x5") (set_tile "taz_s_typ" "12"))
     (if (= taz_s_tmp_type "60x40x5") (set_tile "taz_s_typ" "13"))
     (if (= taz_s_tmp_type "60x40x6") (set_tile "taz_s_typ" "14"))
     (if (= taz_s_tmp_type "60x40x7") (set_tile "taz_s_typ" "15"))
     (if (= taz_s_tmp_type "65x50x5") (set_tile "taz_s_typ" "16"))
     (if (= taz_s_tmp_type "65x50x7") (set_tile "taz_s_typ" "17"))
     (if (= taz_s_tmp_type "65x50x9") (set_tile "taz_s_typ" "18"))
     (if (= taz_s_tmp_type "70x50x6") (set_tile "taz_s_typ" "19"))
     (if (= taz_s_tmp_type "75x50x7") (set_tile "taz_s_typ" "20"))
     (if (= taz_s_tmp_type "75x50x9") (set_tile "taz_s_typ" "21"))
     (if (= taz_s_tmp_type "75x55x5") (set_tile "taz_s_typ" "22"))
     (if (= taz_s_tmp_type "75x55x7") (set_tile "taz_s_typ" "23"))
     (if (= taz_s_tmp_type "75x55x9") (set_tile "taz_s_typ" "24"))
     (if (= taz_s_tmp_type "80x40x6") (set_tile "taz_s_typ" "25"))
     (if (= taz_s_tmp_type "80x40x8") (set_tile "taz_s_typ" "26"))
     (if (= taz_s_tmp_type "80x60x7") (set_tile "taz_s_typ" "27"))
     (if (= taz_s_tmp_type "80x65x8") (set_tile "taz_s_typ" "28"))
     (if (= taz_s_tmp_type "80x65x10") (set_tile "taz_s_typ" "29"))
     (if (= taz_s_tmp_type "90x60x6") (set_tile "taz_s_typ" "30"))
     (if (= taz_s_tmp_type "90x60x8") (set_tile "taz_s_typ" "31"))
     (if (= taz_s_tmp_type "100x50x6") (set_tile "taz_s_typ" "32"))
     (if (= taz_s_tmp_type "100x50x8") (set_tile "taz_s_typ" "33"))
     (if (= taz_s_tmp_type "100x50x10") (set_tile "taz_s_typ" "34"))
     (if (= taz_s_tmp_type "100x65x7") (set_tile "taz_s_typ" "35"))
     (if (= taz_s_tmp_type "100x65x9") (set_tile "taz_s_typ" "36"))
     (if (= taz_s_tmp_type "100x65x11") (set_tile "taz_s_typ" "37"))
     (if (= taz_s_tmp_type "100x75x7") (set_tile "taz_s_typ" "38"))
     (if (= taz_s_tmp_type "100x75x9") (set_tile "taz_s_typ" "39"))
     (if (= taz_s_tmp_type "100x75x11") (set_tile "taz_s_typ" "40"))
     (if (= taz_s_tmp_type "120x80x8") (set_tile "taz_s_typ" "41"))
     (if (= taz_s_tmp_type "120x80x10") (set_tile "taz_s_typ" "42"))
     (if (= taz_s_tmp_type "120x80x12") (set_tile "taz_s_typ" "43"))
     (if (= taz_s_tmp_type "120x80x14") (set_tile "taz_s_typ" "44"))
     (if (= taz_s_tmp_type "130x65x8") (set_tile "taz_s_typ" "45"))
     (if (= taz_s_tmp_type "130x65x10") (set_tile "taz_s_typ" "46"))
     (if (= taz_s_tmp_type "130x65x12") (set_tile "taz_s_typ" "47"))
     (if (= taz_s_tmp_type "130x90x12") (set_tile "taz_s_typ" "48"))
     (if (= taz_s_tmp_type "150x75x9") (set_tile "taz_s_typ" "49"))
     (if (= taz_s_tmp_type "150x75x11") (set_tile "taz_s_typ" "50"))
     (if (= taz_s_tmp_type "150x100x10") (set_tile "taz_s_typ" "51"))
     (if (= taz_s_tmp_type "150x100x12") (set_tile "taz_s_typ" "52"))
     (if (= taz_s_tmp_type "150x100x14") (set_tile "taz_s_typ" "53"))
     (if (= taz_s_tmp_type "160x80x12") (set_tile "taz_s_typ" "54"))
     (if (= taz_s_tmp_type "180x90x10") (set_tile "taz_s_typ" "55"))
     (if (= taz_s_tmp_type "180x90x12") (set_tile "taz_s_typ" "56"))
     (if (= taz_s_tmp_type "200x100x10") (set_tile "taz_s_typ" "57"))
     (if (= taz_s_tmp_type "200x100x12") (set_tile "taz_s_typ" "58"))
     (if (= taz_s_tmp_type "200x100x14") (set_tile "taz_s_typ" "59"))
     (if (= taz_s_tmp_type "200x100x16") (set_tile "taz_s_typ" "60"))
     (if (= taz_s_tmp_type "250x90x10") (set_tile "taz_s_typ" "61"))
     (if (= taz_s_tmp_type "250x90x12") (set_tile "taz_s_typ" "62"))
     (if (= taz_s_tmp_type "250x90x14") (set_tile "taz_s_typ" "63"))
     (if (= taz_s_tmp_type "250x90x16") (set_tile "taz_s_typ" "64"))
     (if 
       (and (not (= taz_s_tmp_type "30x20x3")) 
            (not (= taz_s_tmp_type "30x20x4"))
            (not (= taz_s_tmp_type "40x20x3"))
            (not (= taz_s_tmp_type "40x20x4"))
            (not (= taz_s_tmp_type "40x25x4"))
            (not (= taz_s_tmp_type "45x30x3"))
            (not (= taz_s_tmp_type "45x30x4"))
            (not (= taz_s_tmp_type "45x30x5"))
            (not (= taz_s_tmp_type "50x30x4"))
            (not (= taz_s_tmp_type "50x30x5"))
            (not (= taz_s_tmp_type "50x40x4"))
            (not (= taz_s_tmp_type "50x40x5"))
            (not (= taz_s_tmp_type "60x30x5"))
            (not (= taz_s_tmp_type "60x40x5"))
            (not (= taz_s_tmp_type "60x40x6"))
            (not (= taz_s_tmp_type "60x40x7"))
            (not (= taz_s_tmp_type "65x50x5"))
            (not (= taz_s_tmp_type "65x50x7"))
            (not (= taz_s_tmp_type "65x50x9"))
            (not (= taz_s_tmp_type "70x50x6"))
            (not (= taz_s_tmp_type "75x50x7"))
            (not (= taz_s_tmp_type "75x50x9"))
            (not (= taz_s_tmp_type "75x55x5"))
            (not (= taz_s_tmp_type "75x55x7"))
            (not (= taz_s_tmp_type "75x55x9"))
            (not (= taz_s_tmp_type "80x40x6"))
            (not (= taz_s_tmp_type "80x40x8"))
            (not (= taz_s_tmp_type "80x60x7"))
            (not (= taz_s_tmp_type "80x65x8"))
            (not (= taz_s_tmp_type "80x65x10"))
            (not (= taz_s_tmp_type "90x60x6"))
            (not (= taz_s_tmp_type "90x60x8"))
            (not (= taz_s_tmp_type "100x50x6"))
            (not (= taz_s_tmp_type "100x50x8"))
            (not (= taz_s_tmp_type "100x50x10"))
            (not (= taz_s_tmp_type "100x65x7"))
            (not (= taz_s_tmp_type "100x65x9"))
            (not (= taz_s_tmp_type "100x65x11"))
            (not (= taz_s_tmp_type "100x75x7"))
            (not (= taz_s_tmp_type "100x75x9"))
            (not (= taz_s_tmp_type "100x75x11"))
            (not (= taz_s_tmp_type "120x80x8"))
            (not (= taz_s_tmp_type "120x80x10"))
            (not (= taz_s_tmp_type "120x80x12"))
            (not (= taz_s_tmp_type "120x80x14"))
            (not (= taz_s_tmp_type "130x65x8"))
            (not (= taz_s_tmp_type "130x65x10"))
            (not (= taz_s_tmp_type "130x65x12"))
            (not (= taz_s_tmp_type "130x90x12"))
            (not (= taz_s_tmp_type "150x75x9"))
            (not (= taz_s_tmp_type "150x75x11"))
            (not (= taz_s_tmp_type "150x100x10"))
            (not (= taz_s_tmp_type "150x100x12"))
            (not (= taz_s_tmp_type "150x100x14"))
            (not (= taz_s_tmp_type "160x80x12"))
            (not (= taz_s_tmp_type "180x90x10"))
            (not (= taz_s_tmp_type "180x90x12"))
            (not (= taz_s_tmp_type "200x100x10"))
            (not (= taz_s_tmp_type "200x100x12"))
            (not (= taz_s_tmp_type "200x100x14"))
            (not (= taz_s_tmp_type "200x100x16"))
            (not (= taz_s_tmp_type "250x90x10"))
            (not (= taz_s_tmp_type "250x90x12"))
            (not (= taz_s_tmp_type "250x90x14"))
            (not (= taz_s_tmp_type "250x90x16"))
       )
       (progn (setq taz_s_tmp_type "30x20x3") (set_tile "taz_s_typ" "0"))
     )
    )

    ;; Rury - Rura kwadratowa (SHS)
    ((= taz_s_tmp_family "Rura kwadratowa")
     (if (= taz_s_tmp_type "38x38x2.5") (set_tile "taz_s_typ" "0"))
     (if (= taz_s_tmp_type "38x38x3") (set_tile "taz_s_typ" "1"))
     (if (= taz_s_tmp_type "38x38x3.5") (set_tile "taz_s_typ" "2"))
     (if (= taz_s_tmp_type "50x50x2.5") (set_tile "taz_s_typ" "3"))
     (if (= taz_s_tmp_type "50x50x3") (set_tile "taz_s_typ" "4"))
     (if (= taz_s_tmp_type "50x50x3.5") (set_tile "taz_s_typ" "5"))
     (if (= taz_s_tmp_type "50x50x4") (set_tile "taz_s_typ" "6"))
     (if (= taz_s_tmp_type "50x50x4.5") (set_tile "taz_s_typ" "7"))
     (if (= taz_s_tmp_type "60x60x2.5") (set_tile "taz_s_typ" "8"))
     (if (= taz_s_tmp_type "60x60x3") (set_tile "taz_s_typ" "9"))
     (if (= taz_s_tmp_type "60x60x3.5") (set_tile "taz_s_typ" "10"))
     (if (= taz_s_tmp_type "60x60x4") (set_tile "taz_s_typ" "11"))
     (if (= taz_s_tmp_type "60x60x4.5") (set_tile "taz_s_typ" "12"))
     (if (= taz_s_tmp_type "75x75x2.5") (set_tile "taz_s_typ" "13"))
     (if (= taz_s_tmp_type "75x75x3") (set_tile "taz_s_typ" "14"))
     (if (= taz_s_tmp_type "75x75x3.5") (set_tile "taz_s_typ" "15"))
     (if (= taz_s_tmp_type "75x75x4") (set_tile "taz_s_typ" "16"))
     (if (= taz_s_tmp_type "75x75x4.5") (set_tile "taz_s_typ" "17"))
     (if (= taz_s_tmp_type "75x75x5") (set_tile "taz_s_typ" "18"))
     (if (= taz_s_tmp_type "80x80x2.5") (set_tile "taz_s_typ" "19"))
     (if (= taz_s_tmp_type "80x80x3") (set_tile "taz_s_typ" "20"))
     (if (= taz_s_tmp_type "80x80x3.5") (set_tile "taz_s_typ" "21"))
     (if (= taz_s_tmp_type "80x80x4") (set_tile "taz_s_typ" "22"))
     (if (= taz_s_tmp_type "80x80x4.5") (set_tile "taz_s_typ" "23"))
     (if (= taz_s_tmp_type "80x80x5") (set_tile "taz_s_typ" "24"))
     (if (= taz_s_tmp_type "80x80x6") (set_tile "taz_s_typ" "25"))
     (if (= taz_s_tmp_type "100x100x2.5") (set_tile "taz_s_typ" "26"))
     (if (= taz_s_tmp_type "100x100x3") (set_tile "taz_s_typ" "27"))
     (if (= taz_s_tmp_type "100x100x3.5") (set_tile "taz_s_typ" "28"))
     (if (= taz_s_tmp_type "100x100x4") (set_tile "taz_s_typ" "29"))
     (if (= taz_s_tmp_type "100x100x4.5") (set_tile "taz_s_typ" "30"))
     (if (= taz_s_tmp_type "100x100x5") (set_tile "taz_s_typ" "31"))
     (if (= taz_s_tmp_type "100x100x6") (set_tile "taz_s_typ" "32"))
     (if (= taz_s_tmp_type "120x120x3") (set_tile "taz_s_typ" "33"))
     (if (= taz_s_tmp_type "120x120x3.5") (set_tile "taz_s_typ" "34"))
     (if (= taz_s_tmp_type "120x120x4") (set_tile "taz_s_typ" "35"))
     (if (= taz_s_tmp_type "120x120x4.5") (set_tile "taz_s_typ" "36"))
     (if (= taz_s_tmp_type "120x120x5") (set_tile "taz_s_typ" "37"))
     (if (= taz_s_tmp_type "120x120x6") (set_tile "taz_s_typ" "38"))
     (if (= taz_s_tmp_type "150x150x4") (set_tile "taz_s_typ" "39"))
     (if (= taz_s_tmp_type "150x150x4.5") (set_tile "taz_s_typ" "40"))
     (if (= taz_s_tmp_type "150x150x6") (set_tile "taz_s_typ" "41"))
     (if (= taz_s_tmp_type "150x150x8") (set_tile "taz_s_typ" "42"))
     (if (= taz_s_tmp_type "150x150x10") (set_tile "taz_s_typ" "43"))
     (if (= taz_s_tmp_type "175x175x4") (set_tile "taz_s_typ" "44"))
     (if (= taz_s_tmp_type "175x175x4.5") (set_tile "taz_s_typ" "45"))
     (if (= taz_s_tmp_type "175x175x6") (set_tile "taz_s_typ" "46"))
     (if (= taz_s_tmp_type "175x175x8") (set_tile "taz_s_typ" "47"))
     (if (= taz_s_tmp_type "175x175x10") (set_tile "taz_s_typ" "48"))
     (if (= taz_s_tmp_type "200x200x4.5") (set_tile "taz_s_typ" "49"))
     (if (= taz_s_tmp_type "200x200x6") (set_tile "taz_s_typ" "50"))
     (if (= taz_s_tmp_type "200x200x8") (set_tile "taz_s_typ" "51"))
     (if (= taz_s_tmp_type "200x200x10") (set_tile "taz_s_typ" "52"))
     (if (= taz_s_tmp_type "220x220x6") (set_tile "taz_s_typ" "53"))
     (if (= taz_s_tmp_type "220x220x8") (set_tile "taz_s_typ" "54"))
     (if (= taz_s_tmp_type "220x220x10") (set_tile "taz_s_typ" "55"))
     (if (= taz_s_tmp_type "250x250x4.5") (set_tile "taz_s_typ" "56"))
     (if (= taz_s_tmp_type "250x250x6") (set_tile "taz_s_typ" "57"))
     (if (= taz_s_tmp_type "250x250x8") (set_tile "taz_s_typ" "58"))
     (if (= taz_s_tmp_type "250x250x10") (set_tile "taz_s_typ" "59"))
     (if (= taz_s_tmp_type "285x285x8") (set_tile "taz_s_typ" "60"))
     (if (= taz_s_tmp_type "285x285x10") (set_tile "taz_s_typ" "61"))
     (if 
       (and (not (= taz_s_tmp_type "38x38x2.5")) 
            (not (= taz_s_tmp_type "38x38x3"))
            (not (= taz_s_tmp_type "38x38x3.5"))
            (not (= taz_s_tmp_type "50x50x2.5"))
            (not (= taz_s_tmp_type "50x50x3"))
            (not (= taz_s_tmp_type "50x50x3.5"))
            (not (= taz_s_tmp_type "50x50x4"))
            (not (= taz_s_tmp_type "50x50x4.5"))
            (not (= taz_s_tmp_type "60x60x2.5"))
            (not (= taz_s_tmp_type "60x60x3"))
            (not (= taz_s_tmp_type "60x60x3.5"))
            (not (= taz_s_tmp_type "60x60x4"))
            (not (= taz_s_tmp_type "60x60x4.5"))
            (not (= taz_s_tmp_type "75x75x2.5"))
            (not (= taz_s_tmp_type "75x75x3"))
            (not (= taz_s_tmp_type "75x75x3.5"))
            (not (= taz_s_tmp_type "75x75x4"))
            (not (= taz_s_tmp_type "75x75x4.5"))
            (not (= taz_s_tmp_type "75x75x5"))
            (not (= taz_s_tmp_type "80x80x2.5"))
            (not (= taz_s_tmp_type "80x80x3"))
            (not (= taz_s_tmp_type "80x80x3.5"))
            (not (= taz_s_tmp_type "80x80x4"))
            (not (= taz_s_tmp_type "80x80x4.5"))
            (not (= taz_s_tmp_type "80x80x5"))
            (not (= taz_s_tmp_type "80x80x6"))
            (not (= taz_s_tmp_type "100x100x2.5"))
            (not (= taz_s_tmp_type "100x100x3"))
            (not (= taz_s_tmp_type "100x100x3.5"))
            (not (= taz_s_tmp_type "100x100x4"))
            (not (= taz_s_tmp_type "100x100x4.5"))
            (not (= taz_s_tmp_type "100x100x5"))
            (not (= taz_s_tmp_type "100x100x6"))
            (not (= taz_s_tmp_type "120x120x3"))
            (not (= taz_s_tmp_type "120x120x3.5"))
            (not (= taz_s_tmp_type "120x120x4"))
            (not (= taz_s_tmp_type "120x120x4.5"))
            (not (= taz_s_tmp_type "120x120x5"))
            (not (= taz_s_tmp_type "120x120x6"))
            (not (= taz_s_tmp_type "150x150x4"))
            (not (= taz_s_tmp_type "150x150x4.5"))
            (not (= taz_s_tmp_type "150x150x6"))
            (not (= taz_s_tmp_type "150x150x8"))
            (not (= taz_s_tmp_type "150x150x10"))
            (not (= taz_s_tmp_type "175x175x4"))
            (not (= taz_s_tmp_type "175x175x4.5"))
            (not (= taz_s_tmp_type "175x175x6"))
            (not (= taz_s_tmp_type "175x175x8"))
            (not (= taz_s_tmp_type "175x175x10"))
            (not (= taz_s_tmp_type "200x200x4.5"))
            (not (= taz_s_tmp_type "200x200x6"))
            (not (= taz_s_tmp_type "200x200x8"))
            (not (= taz_s_tmp_type "200x200x10"))
            (not (= taz_s_tmp_type "220x220x6"))
            (not (= taz_s_tmp_type "220x220x8"))
            (not (= taz_s_tmp_type "220x220x10"))
            (not (= taz_s_tmp_type "250x250x4.5"))
            (not (= taz_s_tmp_type "250x250x6"))
            (not (= taz_s_tmp_type "250x250x8"))
            (not (= taz_s_tmp_type "250x250x10"))
            (not (= taz_s_tmp_type "285x285x8"))
            (not (= taz_s_tmp_type "285x285x10"))
       )
       (progn (setq taz_s_tmp_type "38x38x2.5") (set_tile "taz_s_typ" "0"))
     )
    )

    ;; Rury - Rura prostokatna (RHS)
    ((= taz_s_tmp_family "Rura prostokatna")
     (if (= taz_s_tmp_type "50x25x2.5") (set_tile "taz_s_typ" "0"))
     (if (= taz_s_tmp_type "50x25x3") (set_tile "taz_s_typ" "1"))
     (if (= taz_s_tmp_type "50x25x3.5") (set_tile "taz_s_typ" "2"))
     (if (= taz_s_tmp_type "60x40x2.5") (set_tile "taz_s_typ" "3"))
     (if (= taz_s_tmp_type "60x40x3") (set_tile "taz_s_typ" "4"))
     (if (= taz_s_tmp_type "60x40x3.5") (set_tile "taz_s_typ" "5"))
     (if (= taz_s_tmp_type "60x40x4") (set_tile "taz_s_typ" "6"))
     (if (= taz_s_tmp_type "60x40x4.5") (set_tile "taz_s_typ" "7"))
     (if (= taz_s_tmp_type "76x38x2.5") (set_tile "taz_s_typ" "8"))
     (if (= taz_s_tmp_type "76x38x3") (set_tile "taz_s_typ" "9"))
     (if (= taz_s_tmp_type "76x38x3.5") (set_tile "taz_s_typ" "10"))
     (if (= taz_s_tmp_type "76x38x4") (set_tile "taz_s_typ" "11"))
     (if (= taz_s_tmp_type "76x38x4.5") (set_tile "taz_s_typ" "12"))
     (if (= taz_s_tmp_type "80x40x2.5") (set_tile "taz_s_typ" "13"))
     (if (= taz_s_tmp_type "80x40x3") (set_tile "taz_s_typ" "14"))
     (if (= taz_s_tmp_type "80x40x3.5") (set_tile "taz_s_typ" "15"))
     (if (= taz_s_tmp_type "80x40x4") (set_tile "taz_s_typ" "16"))
     (if (= taz_s_tmp_type "80x40x4.5") (set_tile "taz_s_typ" "17"))
     (if (= taz_s_tmp_type "100x50x2.5") (set_tile "taz_s_typ" "18"))
     (if (= taz_s_tmp_type "100x50x3") (set_tile "taz_s_typ" "19"))
     (if (= taz_s_tmp_type "100x50x3.5") (set_tile "taz_s_typ" "20"))
     (if (= taz_s_tmp_type "100x50x4") (set_tile "taz_s_typ" "21"))
     (if (= taz_s_tmp_type "100x50x4.5") (set_tile "taz_s_typ" "22"))
     (if (= taz_s_tmp_type "100x50x5") (set_tile "taz_s_typ" "23"))
     (if (= taz_s_tmp_type "100x50x6") (set_tile "taz_s_typ" "24"))
     (if (= taz_s_tmp_type "120x60x3") (set_tile "taz_s_typ" "25"))
     (if (= taz_s_tmp_type "120x60x3.5") (set_tile "taz_s_typ" "26"))
     (if (= taz_s_tmp_type "120x60x4") (set_tile "taz_s_typ" "27"))
     (if (= taz_s_tmp_type "120x60x4.5") (set_tile "taz_s_typ" "28"))
     (if (= taz_s_tmp_type "120x60x5") (set_tile "taz_s_typ" "29"))
     (if (= taz_s_tmp_type "120x60x6") (set_tile "taz_s_typ" "30"))
     (if (= taz_s_tmp_type "150x100x3") (set_tile "taz_s_typ" "31"))
     (if (= taz_s_tmp_type "150x100x3.5") (set_tile "taz_s_typ" "32"))
     (if (= taz_s_tmp_type "150x100x4") (set_tile "taz_s_typ" "33"))
     (if (= taz_s_tmp_type "150x100x4.5") (set_tile "taz_s_typ" "34"))
     (if (= taz_s_tmp_type "150x100x5") (set_tile "taz_s_typ" "35"))
     (if (= taz_s_tmp_type "150x100x6") (set_tile "taz_s_typ" "36"))
     (if (= taz_s_tmp_type "160x80x3") (set_tile "taz_s_typ" "37"))
     (if (= taz_s_tmp_type "160x80x3.5") (set_tile "taz_s_typ" "38"))
     (if (= taz_s_tmp_type "160x80x4") (set_tile "taz_s_typ" "39"))
     (if (= taz_s_tmp_type "160x80x4.5") (set_tile "taz_s_typ" "40"))
     (if (= taz_s_tmp_type "160x80x5") (set_tile "taz_s_typ" "41"))
     (if (= taz_s_tmp_type "160x80x6") (set_tile "taz_s_typ" "42"))
     (if (= taz_s_tmp_type "200x100x4") (set_tile "taz_s_typ" "43"))
     (if (= taz_s_tmp_type "200x100x4.5") (set_tile "taz_s_typ" "44"))
     (if (= taz_s_tmp_type "200x100x6") (set_tile "taz_s_typ" "45"))
     (if (= taz_s_tmp_type "200x100x8") (set_tile "taz_s_typ" "46"))
     (if (= taz_s_tmp_type "200x100x10") (set_tile "taz_s_typ" "47"))
     (if (= taz_s_tmp_type "200x150x4") (set_tile "taz_s_typ" "48"))
     (if (= taz_s_tmp_type "200x150x4.5") (set_tile "taz_s_typ" "49"))
     (if (= taz_s_tmp_type "200x150x6") (set_tile "taz_s_typ" "50"))
     (if (= taz_s_tmp_type "200x150x8") (set_tile "taz_s_typ" "51"))
     (if (= taz_s_tmp_type "200x150x10") (set_tile "taz_s_typ" "52"))
     (if (= taz_s_tmp_type "250x100x4") (set_tile "taz_s_typ" "53"))
     (if (= taz_s_tmp_type "250x100x4.5") (set_tile "taz_s_typ" "54"))
     (if (= taz_s_tmp_type "250x100x6") (set_tile "taz_s_typ" "55"))
     (if (= taz_s_tmp_type "250x100x8") (set_tile "taz_s_typ" "56"))
     (if (= taz_s_tmp_type "250x100x10") (set_tile "taz_s_typ" "57"))
     (if (= taz_s_tmp_type "250x150x6") (set_tile "taz_s_typ" "58"))
     (if (= taz_s_tmp_type "250x150x8") (set_tile "taz_s_typ" "59"))
     (if (= taz_s_tmp_type "250x150x10") (set_tile "taz_s_typ" "60"))
     (if (= taz_s_tmp_type "300x140x6") (set_tile "taz_s_typ" "61"))
     (if (= taz_s_tmp_type "300x140x8") (set_tile "taz_s_typ" "62"))
     (if (= taz_s_tmp_type "300x140x10") (set_tile "taz_s_typ" "63"))
     (if (= taz_s_tmp_type "320x200x6") (set_tile "taz_s_typ" "64"))
     (if (= taz_s_tmp_type "320x200x8") (set_tile "taz_s_typ" "65"))
     (if (= taz_s_tmp_type "320x200x10") (set_tile "taz_s_typ" "66"))
     (if (= taz_s_tmp_type "340x180x6") (set_tile "taz_s_typ" "67"))
     (if (= taz_s_tmp_type "340x180x8") (set_tile "taz_s_typ" "68"))
     (if (= taz_s_tmp_type "340x180x10") (set_tile "taz_s_typ" "69"))
     (if 
       (and (not (= taz_s_tmp_type "50x25x2.5")) 
            (not (= taz_s_tmp_type "50x25x3"))
            (not (= taz_s_tmp_type "50x25x3.5"))
            (not (= taz_s_tmp_type "60x40x2.5"))
            (not (= taz_s_tmp_type "60x40x3"))
            (not (= taz_s_tmp_type "60x40x3.5"))
            (not (= taz_s_tmp_type "60x40x4"))
            (not (= taz_s_tmp_type "60x40x4.5"))
            (not (= taz_s_tmp_type "76x38x2.5"))
            (not (= taz_s_tmp_type "76x38x3"))
            (not (= taz_s_tmp_type "76x38x3.5"))
            (not (= taz_s_tmp_type "76x38x4"))
            (not (= taz_s_tmp_type "76x38x4.5"))
            (not (= taz_s_tmp_type "80x40x2.5"))
            (not (= taz_s_tmp_type "80x40x3"))
            (not (= taz_s_tmp_type "80x40x3.5"))
            (not (= taz_s_tmp_type "80x40x4"))
            (not (= taz_s_tmp_type "80x40x4.5"))
            (not (= taz_s_tmp_type "100x50x2.5"))
            (not (= taz_s_tmp_type "100x50x3"))
            (not (= taz_s_tmp_type "100x50x3.5"))
            (not (= taz_s_tmp_type "100x50x4"))
            (not (= taz_s_tmp_type "100x50x4.5"))
            (not (= taz_s_tmp_type "100x50x5"))
            (not (= taz_s_tmp_type "100x50x6"))
            (not (= taz_s_tmp_type "120x60x3"))
            (not (= taz_s_tmp_type "120x60x3.5"))
            (not (= taz_s_tmp_type "120x60x4"))
            (not (= taz_s_tmp_type "120x60x4.5"))
            (not (= taz_s_tmp_type "120x60x5"))
            (not (= taz_s_tmp_type "120x60x6"))
            (not (= taz_s_tmp_type "150x100x3"))
            (not (= taz_s_tmp_type "150x100x3.5"))
            (not (= taz_s_tmp_type "150x100x4"))
            (not (= taz_s_tmp_type "150x100x4.5"))
            (not (= taz_s_tmp_type "150x100x5"))
            (not (= taz_s_tmp_type "150x100x6"))
            (not (= taz_s_tmp_type "160x80x3"))
            (not (= taz_s_tmp_type "160x80x3.5"))
            (not (= taz_s_tmp_type "160x80x4"))
            (not (= taz_s_tmp_type "160x80x4.5"))
            (not (= taz_s_tmp_type "160x80x5"))
            (not (= taz_s_tmp_type "160x80x6"))
            (not (= taz_s_tmp_type "200x100x4"))
            (not (= taz_s_tmp_type "200x100x4.5"))
            (not (= taz_s_tmp_type "200x100x6"))
            (not (= taz_s_tmp_type "200x100x8"))
            (not (= taz_s_tmp_type "200x100x10"))
            (not (= taz_s_tmp_type "200x150x4"))
            (not (= taz_s_tmp_type "200x150x4.5"))
            (not (= taz_s_tmp_type "200x150x6"))
            (not (= taz_s_tmp_type "200x150x8"))
            (not (= taz_s_tmp_type "200x150x10"))
            (not (= taz_s_tmp_type "250x100x4"))
            (not (= taz_s_tmp_type "250x100x4.5"))
            (not (= taz_s_tmp_type "250x100x6"))
            (not (= taz_s_tmp_type "250x100x8"))
            (not (= taz_s_tmp_type "250x100x10"))
            (not (= taz_s_tmp_type "250x150x6"))
            (not (= taz_s_tmp_type "250x150x8"))
            (not (= taz_s_tmp_type "250x150x10"))
            (not (= taz_s_tmp_type "300x140x6"))
            (not (= taz_s_tmp_type "300x140x8"))
            (not (= taz_s_tmp_type "300x140x10"))
            (not (= taz_s_tmp_type "320x200x6"))
            (not (= taz_s_tmp_type "320x200x8"))
            (not (= taz_s_tmp_type "320x200x10"))
            (not (= taz_s_tmp_type "340x180x6"))
            (not (= taz_s_tmp_type "340x180x8"))
            (not (= taz_s_tmp_type "340x180x10"))
       )
       (progn (setq taz_s_tmp_type "50x25x2.5") (set_tile "taz_s_typ" "0"))
     )
    )

    ;; Rury - Rura okragla (CHS)
    ((= taz_s_tmp_family "Rura okragla")
     (if (= taz_s_tmp_type "508x12.7") (set_tile "taz_s_typ" "0"))
     (if (= taz_s_tmp_type "508x9.5") (set_tile "taz_s_typ" "1"))
     (if (= taz_s_tmp_type "457.2x12.7") (set_tile "taz_s_typ" "2"))
     (if (= taz_s_tmp_type "457.2x9.5") (set_tile "taz_s_typ" "3"))
     (if (= taz_s_tmp_type "406.4x12.7") (set_tile "taz_s_typ" "4"))
     (if (= taz_s_tmp_type "406.4x11.1") (set_tile "taz_s_typ" "5"))
     (if (= taz_s_tmp_type "406.4x9.5") (set_tile "taz_s_typ" "6"))
     (if (= taz_s_tmp_type "406.4x7.9") (set_tile "taz_s_typ" "7"))
     (if (= taz_s_tmp_type "355.6x12.7") (set_tile "taz_s_typ" "8"))
     (if (= taz_s_tmp_type "355.6x9.5") (set_tile "taz_s_typ" "9"))
     (if (= taz_s_tmp_type "355.6x7.9") (set_tile "taz_s_typ" "10"))
     (if (= taz_s_tmp_type "323.9x12.7") (set_tile "taz_s_typ" "11"))
     (if (= taz_s_tmp_type "323.9x9.5") (set_tile "taz_s_typ" "12"))
     (if (= taz_s_tmp_type "323.9x6.4") (set_tile "taz_s_typ" "13"))
     (if (= taz_s_tmp_type "317.5x15.9") (set_tile "taz_s_typ" "14"))
     (if (= taz_s_tmp_type "317.5x12.7") (set_tile "taz_s_typ" "15"))
     (if (= taz_s_tmp_type "317.5x9.5") (set_tile "taz_s_typ" "16"))
     (if (= taz_s_tmp_type "317.5x7.9") (set_tile "taz_s_typ" "17"))
     (if (= taz_s_tmp_type "317.5x6.4") (set_tile "taz_s_typ" "18"))
     (if (= taz_s_tmp_type "317.5x4.8") (set_tile "taz_s_typ" "19"))
     (if (= taz_s_tmp_type "312.8x15.9") (set_tile "taz_s_typ" "20"))
     (if (= taz_s_tmp_type "312.8x12.7") (set_tile "taz_s_typ" "21"))
     (if (= taz_s_tmp_type "312.8x9.5") (set_tile "taz_s_typ" "22"))
     (if (= taz_s_tmp_type "312.8x7.9") (set_tile "taz_s_typ" "23"))
     (if (= taz_s_tmp_type "312.8x6.4") (set_tile "taz_s_typ" "24"))
     (if (= taz_s_tmp_type "312.8x4.8") (set_tile "taz_s_typ" "25"))
     (if (= taz_s_tmp_type "311.2x15.9") (set_tile "taz_s_typ" "26"))
     (if (= taz_s_tmp_type "311.2x12.7") (set_tile "taz_s_typ" "27"))
     (if (= taz_s_tmp_type "311.2x9.5") (set_tile "taz_s_typ" "28"))
     (if (= taz_s_tmp_type "311.2x7.9") (set_tile "taz_s_typ" "29"))
     (if (= taz_s_tmp_type "311.2x6.4") (set_tile "taz_s_typ" "30"))
     (if (= taz_s_tmp_type "311.2x4.8") (set_tile "taz_s_typ" "31"))
     (if (= taz_s_tmp_type "285.8x15.9") (set_tile "taz_s_typ" "32"))
     (if (= taz_s_tmp_type "285.8x12.7") (set_tile "taz_s_typ" "33"))
     (if (= taz_s_tmp_type "285.8x9.5") (set_tile "taz_s_typ" "34"))
     (if (= taz_s_tmp_type "285.8x7.9") (set_tile "taz_s_typ" "35"))
     (if (= taz_s_tmp_type "285.8x6.4") (set_tile "taz_s_typ" "36"))
     (if (= taz_s_tmp_type "285.8x4.8") (set_tile "taz_s_typ" "37"))
     (if (= taz_s_tmp_type "273.1x12.7") (set_tile "taz_s_typ" "38"))
     (if (= taz_s_tmp_type "273.1x9.3") (set_tile "taz_s_typ" "39"))
     (if (= taz_s_tmp_type "273.1x6.4") (set_tile "taz_s_typ" "40"))
     (if (= taz_s_tmp_type "254x15.9") (set_tile "taz_s_typ" "41"))
     (if (= taz_s_tmp_type "254x12.7") (set_tile "taz_s_typ" "42"))
     (if (= taz_s_tmp_type "254x9.5") (set_tile "taz_s_typ" "43"))
     (if (= taz_s_tmp_type "254x7.9") (set_tile "taz_s_typ" "44"))
     (if (= taz_s_tmp_type "254x6.4") (set_tile "taz_s_typ" "45"))
     (if (= taz_s_tmp_type "254x4.8") (set_tile "taz_s_typ" "46"))
     (if (= taz_s_tmp_type "244.5x12.7") (set_tile "taz_s_typ" "47"))
     (if (= taz_s_tmp_type "244.5x9.5") (set_tile "taz_s_typ" "48"))
     (if (= taz_s_tmp_type "244.5x7.9") (set_tile "taz_s_typ" "49"))
     (if (= taz_s_tmp_type "244.5x6.4") (set_tile "taz_s_typ" "50"))
     (if (= taz_s_tmp_type "222.3x12.7") (set_tile "taz_s_typ" "51"))
     (if (= taz_s_tmp_type "222.3x9.5") (set_tile "taz_s_typ" "52"))
     (if (= taz_s_tmp_type "222.3x7.9") (set_tile "taz_s_typ" "53"))
     (if (= taz_s_tmp_type "222.3x6.4") (set_tile "taz_s_typ" "54"))
     (if (= taz_s_tmp_type "222.3x4.8") (set_tile "taz_s_typ" "55"))
     (if (= taz_s_tmp_type "219.1x12.7") (set_tile "taz_s_typ" "56"))
     (if (= taz_s_tmp_type "219.1x9.5") (set_tile "taz_s_typ" "57"))
     (if (= taz_s_tmp_type "219.1x8.2") (set_tile "taz_s_typ" "58"))
     (if (= taz_s_tmp_type "219.1x6.4") (set_tile "taz_s_typ" "59"))
     (if (= taz_s_tmp_type "219.1x4.8") (set_tile "taz_s_typ" "60"))
     (if (= taz_s_tmp_type "193.7x9.5") (set_tile "taz_s_typ" "61"))
     (if (= taz_s_tmp_type "193.7x8.3") (set_tile "taz_s_typ" "62"))
     (if (= taz_s_tmp_type "193.7x3.2") (set_tile "taz_s_typ" "63"))
     (if (= taz_s_tmp_type "190.5x12.7") (set_tile "taz_s_typ" "64"))
     (if (= taz_s_tmp_type "190.5x9.5") (set_tile "taz_s_typ" "65"))
     (if (= taz_s_tmp_type "190.5x7.9") (set_tile "taz_s_typ" "66"))
     (if (= taz_s_tmp_type "190.5x6.4") (set_tile "taz_s_typ" "67"))
     (if (= taz_s_tmp_type "190.5x4.8") (set_tile "taz_s_typ" "68"))
     (if (= taz_s_tmp_type "177.8x12.7") (set_tile "taz_s_typ" "69"))
     (if (= taz_s_tmp_type "177.8x9.5") (set_tile "taz_s_typ" "70"))
     (if (= taz_s_tmp_type "177.8x7.9") (set_tile "taz_s_typ" "71"))
     (if (= taz_s_tmp_type "177.8x6.4") (set_tile "taz_s_typ" "72"))
     (if (= taz_s_tmp_type "177.8x4.8") (set_tile "taz_s_typ" "73"))
     (if (= taz_s_tmp_type "177.8x3.2") (set_tile "taz_s_typ" "74"))
     (if (= taz_s_tmp_type "174.6x12.7") (set_tile "taz_s_typ" "75"))
     (if (= taz_s_tmp_type "174.6x9.5") (set_tile "taz_s_typ" "76"))
     (if (= taz_s_tmp_type "174.6x7.9") (set_tile "taz_s_typ" "77"))
     (if (= taz_s_tmp_type "174.6x6.4") (set_tile "taz_s_typ" "78"))
     (if (= taz_s_tmp_type "174.6x4.8") (set_tile "taz_s_typ" "79"))
     (if (= taz_s_tmp_type "168.3x12.7") (set_tile "taz_s_typ" "80"))
     (if (= taz_s_tmp_type "168.3x11") (set_tile "taz_s_typ" "81"))
     (if (= taz_s_tmp_type "168.3x9.5") (set_tile "taz_s_typ" "82"))
     (if (= taz_s_tmp_type "168.3x7.9") (set_tile "taz_s_typ" "83"))
     (if (= taz_s_tmp_type "168.3x7.1") (set_tile "taz_s_typ" "84"))
     (if (= taz_s_tmp_type "168.3x6.4") (set_tile "taz_s_typ" "85"))
     (if (= taz_s_tmp_type "168.3x4.8") (set_tile "taz_s_typ" "86"))
     (if (= taz_s_tmp_type "168.3x3.2") (set_tile "taz_s_typ" "87"))
     (if (= taz_s_tmp_type "155.6x12.7") (set_tile "taz_s_typ" "88"))
     (if (= taz_s_tmp_type "155.6x9.5") (set_tile "taz_s_typ" "89"))
     (if (= taz_s_tmp_type "155.6x7.9") (set_tile "taz_s_typ" "90"))
     (if (= taz_s_tmp_type "155.6x6.4") (set_tile "taz_s_typ" "91"))
     (if (= taz_s_tmp_type "155.6x4.8") (set_tile "taz_s_typ" "92"))
     (if (= taz_s_tmp_type "152.4x12.7") (set_tile "taz_s_typ" "93"))
     (if (= taz_s_tmp_type "152.4x9.5") (set_tile "taz_s_typ" "94"))
     (if (= taz_s_tmp_type "152.4x7.9") (set_tile "taz_s_typ" "95"))
     (if (= taz_s_tmp_type "152.4x7.1") (set_tile "taz_s_typ" "96"))
     (if (= taz_s_tmp_type "152.4x6.4") (set_tile "taz_s_typ" "97"))
     (if (= taz_s_tmp_type "152.4x4.8") (set_tile "taz_s_typ" "98"))
     (if (= taz_s_tmp_type "152.4x3.2") (set_tile "taz_s_typ" "99"))
     (if (= taz_s_tmp_type "141.3x9.5") (set_tile "taz_s_typ" "100"))
     (if (= taz_s_tmp_type "141.3x6.6") (set_tile "taz_s_typ" "101"))
     (if (= taz_s_tmp_type "141.3x4.8") (set_tile "taz_s_typ" "102"))
     (if (= taz_s_tmp_type "141.3x3.4") (set_tile "taz_s_typ" "103"))
     (if (= taz_s_tmp_type "139.7x12.7") (set_tile "taz_s_typ" "104"))
     (if (= taz_s_tmp_type "139.7x9.5") (set_tile "taz_s_typ" "105"))
     (if (= taz_s_tmp_type "139.7x6.6") (set_tile "taz_s_typ" "106"))
     (if (= taz_s_tmp_type "127x12.7") (set_tile "taz_s_typ" "107"))
     (if (= taz_s_tmp_type "127x9.5") (set_tile "taz_s_typ" "108"))
     (if (= taz_s_tmp_type "127x7.9") (set_tile "taz_s_typ" "109"))
     (if (= taz_s_tmp_type "127x6.6") (set_tile "taz_s_typ" "110"))
     (if (= taz_s_tmp_type "127x6.4") (set_tile "taz_s_typ" "111"))
     (if (= taz_s_tmp_type "127x4.8") (set_tile "taz_s_typ" "112"))
     (if (= taz_s_tmp_type "127x3.2") (set_tile "taz_s_typ" "113"))
     (if (= taz_s_tmp_type "114.3x8.6") (set_tile "taz_s_typ" "114"))
     (if (= taz_s_tmp_type "114.3x6") (set_tile "taz_s_typ" "115"))
     (if (= taz_s_tmp_type "114.3x4.8") (set_tile "taz_s_typ" "116"))
     (if (= taz_s_tmp_type "114.3x3.2") (set_tile "taz_s_typ" "117"))
     (if (= taz_s_tmp_type "101.6x8.6") (set_tile "taz_s_typ" "118"))
     (if (= taz_s_tmp_type "101.6x8") (set_tile "taz_s_typ" "119"))
     (if (= taz_s_tmp_type "101.6x6.4") (set_tile "taz_s_typ" "120"))
     (if (= taz_s_tmp_type "101.6x6") (set_tile "taz_s_typ" "121"))
     (if (= taz_s_tmp_type "101.6x5.7") (set_tile "taz_s_typ" "122"))
     (if (= taz_s_tmp_type "101.6x5.6") (set_tile "taz_s_typ" "123"))
     (if (= taz_s_tmp_type "101.6x4.8") (set_tile "taz_s_typ" "124"))
     (if (= taz_s_tmp_type "101.6x3.2") (set_tile "taz_s_typ" "125"))
     (if (= taz_s_tmp_type "88.9x8") (set_tile "taz_s_typ" "126"))
     (if (= taz_s_tmp_type "88.9x7.6") (set_tile "taz_s_typ" "127"))
     (if (= taz_s_tmp_type "88.9x6.4") (set_tile "taz_s_typ" "128"))
     (if (= taz_s_tmp_type "88.9x5.5") (set_tile "taz_s_typ" "129"))
     (if (= taz_s_tmp_type "88.9x5.2") (set_tile "taz_s_typ" "130"))
     (if (= taz_s_tmp_type "88.9x4.8") (set_tile "taz_s_typ" "131"))
     (if (= taz_s_tmp_type "88.9x3.2") (set_tile "taz_s_typ" "132"))
     (if (= taz_s_tmp_type "76.2x7.6") (set_tile "taz_s_typ" "133"))
     (if (= taz_s_tmp_type "76.2x6.4") (set_tile "taz_s_typ" "134"))
     (if (= taz_s_tmp_type "76.2x5.5") (set_tile "taz_s_typ" "135"))
     (if (= taz_s_tmp_type "76.2x5.2") (set_tile "taz_s_typ" "136"))
     (if (= taz_s_tmp_type "76.2x4.8") (set_tile "taz_s_typ" "137"))
     (if (= taz_s_tmp_type "76.2x3.9") (set_tile "taz_s_typ" "138"))
     (if (= taz_s_tmp_type "76.2x3.4") (set_tile "taz_s_typ" "139"))
     (if (= taz_s_tmp_type "76.2x3") (set_tile "taz_s_typ" "140"))
     (if (= taz_s_tmp_type "73x6.4") (set_tile "taz_s_typ" "141"))
     (if (= taz_s_tmp_type "73x5.2") (set_tile "taz_s_typ" "142"))
     (if (= taz_s_tmp_type "73x4.8") (set_tile "taz_s_typ" "143"))
     (if (= taz_s_tmp_type "73x3.2") (set_tile "taz_s_typ" "144"))
     (if (= taz_s_tmp_type "63.5x6.4") (set_tile "taz_s_typ" "145"))
     (if (= taz_s_tmp_type "63.5x4.8") (set_tile "taz_s_typ" "146"))
     (if (= taz_s_tmp_type "63.5x3.2") (set_tile "taz_s_typ" "147"))
     (if (= taz_s_tmp_type "60.3x6.4") (set_tile "taz_s_typ" "148"))
     (if (= taz_s_tmp_type "60.3x5.5") (set_tile "taz_s_typ" "149"))
     (if (= taz_s_tmp_type "60.3x4.8") (set_tile "taz_s_typ" "150"))
     (if (= taz_s_tmp_type "60.3x3.9") (set_tile "taz_s_typ" "151"))
     (if (= taz_s_tmp_type "60.3x3.2") (set_tile "taz_s_typ" "152"))
     (if (= taz_s_tmp_type "48.3x3.7") (set_tile "taz_s_typ" "153"))
     (if (= taz_s_tmp_type "42.2x3.6") (set_tile "taz_s_typ" "154"))
     (if 
       (and (not (= taz_s_tmp_type "508x12.7")) 
            (not (= taz_s_tmp_type "508x9.5"))
            (not (= taz_s_tmp_type "457.2x12.7"))
            (not (= taz_s_tmp_type "457.2x9.5"))
            (not (= taz_s_tmp_type "406.4x12.7"))
            (not (= taz_s_tmp_type "406.4x11.1"))
            (not (= taz_s_tmp_type "406.4x9.5"))
            (not (= taz_s_tmp_type "406.4x7.9"))
            (not (= taz_s_tmp_type "355.6x12.7"))
            (not (= taz_s_tmp_type "355.6x9.5"))
            (not (= taz_s_tmp_type "355.6x7.9"))
            (not (= taz_s_tmp_type "323.9x12.7"))
            (not (= taz_s_tmp_type "323.9x9.5"))
            (not (= taz_s_tmp_type "323.9x6.4"))
            (not (= taz_s_tmp_type "317.5x15.9"))
            (not (= taz_s_tmp_type "317.5x12.7"))
            (not (= taz_s_tmp_type "317.5x9.5"))
            (not (= taz_s_tmp_type "317.5x7.9"))
            (not (= taz_s_tmp_type "317.5x6.4"))
            (not (= taz_s_tmp_type "317.5x4.8"))
            (not (= taz_s_tmp_type "312.8x15.9"))
            (not (= taz_s_tmp_type "312.8x12.7"))
            (not (= taz_s_tmp_type "312.8x9.5"))
            (not (= taz_s_tmp_type "312.8x7.9"))
            (not (= taz_s_tmp_type "312.8x6.4"))
            (not (= taz_s_tmp_type "312.8x4.8"))
            (not (= taz_s_tmp_type "311.2x15.9"))
            (not (= taz_s_tmp_type "311.2x12.7"))
            (not (= taz_s_tmp_type "311.2x9.5"))
            (not (= taz_s_tmp_type "311.2x7.9"))
            (not (= taz_s_tmp_type "311.2x6.4"))
            (not (= taz_s_tmp_type "311.2x4.8"))
            (not (= taz_s_tmp_type "285.8x15.9"))
            (not (= taz_s_tmp_type "285.8x12.7"))
            (not (= taz_s_tmp_type "285.8x9.5"))
            (not (= taz_s_tmp_type "285.8x7.9"))
            (not (= taz_s_tmp_type "285.8x6.4"))
            (not (= taz_s_tmp_type "285.8x4.8"))
            (not (= taz_s_tmp_type "273.1x12.7"))
            (not (= taz_s_tmp_type "273.1x9.3"))
            (not (= taz_s_tmp_type "273.1x6.4"))
            (not (= taz_s_tmp_type "254x15.9"))
            (not (= taz_s_tmp_type "254x12.7"))
            (not (= taz_s_tmp_type "254x9.5"))
            (not (= taz_s_tmp_type "254x7.9"))
            (not (= taz_s_tmp_type "254x6.4"))
            (not (= taz_s_tmp_type "254x4.8"))
            (not (= taz_s_tmp_type "244.5x12.7"))
            (not (= taz_s_tmp_type "244.5x9.5"))
            (not (= taz_s_tmp_type "244.5x7.9"))
            (not (= taz_s_tmp_type "244.5x6.4"))
            (not (= taz_s_tmp_type "222.3x12.7"))
            (not (= taz_s_tmp_type "222.3x9.5"))
            (not (= taz_s_tmp_type "222.3x7.9"))
            (not (= taz_s_tmp_type "222.3x6.4"))
            (not (= taz_s_tmp_type "222.3x4.8"))
            (not (= taz_s_tmp_type "219.1x12.7"))
            (not (= taz_s_tmp_type "219.1x9.5"))
            (not (= taz_s_tmp_type "219.1x8.2"))
            (not (= taz_s_tmp_type "219.1x6.4"))
            (not (= taz_s_tmp_type "219.1x4.8"))
            (not (= taz_s_tmp_type "193.7x9.5"))
            (not (= taz_s_tmp_type "193.7x8.3"))
            (not (= taz_s_tmp_type "193.7x3.2"))
            (not (= taz_s_tmp_type "190.5x12.7"))
            (not (= taz_s_tmp_type "190.5x9.5"))
            (not (= taz_s_tmp_type "190.5x7.9"))
            (not (= taz_s_tmp_type "190.5x6.4"))
            (not (= taz_s_tmp_type "190.5x4.8"))
            (not (= taz_s_tmp_type "177.8x12.7"))
            (not (= taz_s_tmp_type "177.8x9.5"))
            (not (= taz_s_tmp_type "177.8x7.9"))
            (not (= taz_s_tmp_type "177.8x6.4"))
            (not (= taz_s_tmp_type "177.8x4.8"))
            (not (= taz_s_tmp_type "177.8x3.2"))
            (not (= taz_s_tmp_type "174.6x12.7"))
            (not (= taz_s_tmp_type "174.6x9.5"))
            (not (= taz_s_tmp_type "174.6x7.9"))
            (not (= taz_s_tmp_type "174.6x6.4"))
            (not (= taz_s_tmp_type "174.6x4.8"))
            (not (= taz_s_tmp_type "168.3x12.7"))
            (not (= taz_s_tmp_type "168.3x11"))
            (not (= taz_s_tmp_type "168.3x9.5"))
            (not (= taz_s_tmp_type "168.3x7.9"))
            (not (= taz_s_tmp_type "168.3x7.1"))
            (not (= taz_s_tmp_type "168.3x6.4"))
            (not (= taz_s_tmp_type "168.3x4.8"))
            (not (= taz_s_tmp_type "168.3x3.2"))
            (not (= taz_s_tmp_type "155.6x12.7"))
            (not (= taz_s_tmp_type "155.6x9.5"))
            (not (= taz_s_tmp_type "155.6x7.9"))
            (not (= taz_s_tmp_type "155.6x6.4"))
            (not (= taz_s_tmp_type "155.6x4.8"))
            (not (= taz_s_tmp_type "152.4x12.7"))
            (not (= taz_s_tmp_type "152.4x9.5"))
            (not (= taz_s_tmp_type "152.4x7.9"))
            (not (= taz_s_tmp_type "152.4x7.1"))
            (not (= taz_s_tmp_type "152.4x6.4"))
            (not (= taz_s_tmp_type "152.4x4.8"))
            (not (= taz_s_tmp_type "152.4x3.2"))
            (not (= taz_s_tmp_type "141.3x9.5"))
            (not (= taz_s_tmp_type "141.3x6.6"))
            (not (= taz_s_tmp_type "141.3x4.8"))
            (not (= taz_s_tmp_type "141.3x3.4"))
            (not (= taz_s_tmp_type "139.7x12.7"))
            (not (= taz_s_tmp_type "139.7x9.5"))
            (not (= taz_s_tmp_type "139.7x6.6"))
            (not (= taz_s_tmp_type "127x12.7"))
            (not (= taz_s_tmp_type "127x9.5"))
            (not (= taz_s_tmp_type "127x7.9"))
            (not (= taz_s_tmp_type "127x6.6"))
            (not (= taz_s_tmp_type "127x6.4"))
            (not (= taz_s_tmp_type "127x4.8"))
            (not (= taz_s_tmp_type "127x3.2"))
            (not (= taz_s_tmp_type "114.3x8.6"))
            (not (= taz_s_tmp_type "114.3x6"))
            (not (= taz_s_tmp_type "114.3x4.8"))
            (not (= taz_s_tmp_type "114.3x3.2"))
            (not (= taz_s_tmp_type "101.6x8.6"))
            (not (= taz_s_tmp_type "101.6x8"))
            (not (= taz_s_tmp_type "101.6x6.4"))
            (not (= taz_s_tmp_type "101.6x6"))
            (not (= taz_s_tmp_type "101.6x5.7"))
            (not (= taz_s_tmp_type "101.6x5.6"))
            (not (= taz_s_tmp_type "101.6x4.8"))
            (not (= taz_s_tmp_type "101.6x3.2"))
            (not (= taz_s_tmp_type "88.9x8"))
            (not (= taz_s_tmp_type "88.9x7.6"))
            (not (= taz_s_tmp_type "88.9x6.4"))
            (not (= taz_s_tmp_type "88.9x5.5"))
            (not (= taz_s_tmp_type "88.9x5.2"))
            (not (= taz_s_tmp_type "88.9x4.8"))
            (not (= taz_s_tmp_type "88.9x3.2"))
            (not (= taz_s_tmp_type "76.2x7.6"))
            (not (= taz_s_tmp_type "76.2x6.4"))
            (not (= taz_s_tmp_type "76.2x5.5"))
            (not (= taz_s_tmp_type "76.2x5.2"))
            (not (= taz_s_tmp_type "76.2x4.8"))
            (not (= taz_s_tmp_type "76.2x3.9"))
            (not (= taz_s_tmp_type "76.2x3.4"))
            (not (= taz_s_tmp_type "76.2x3"))
            (not (= taz_s_tmp_type "73x6.4"))
            (not (= taz_s_tmp_type "73x5.2"))
            (not (= taz_s_tmp_type "73x4.8"))
            (not (= taz_s_tmp_type "73x3.2"))
            (not (= taz_s_tmp_type "63.5x6.4"))
            (not (= taz_s_tmp_type "63.5x4.8"))
            (not (= taz_s_tmp_type "63.5x3.2"))
            (not (= taz_s_tmp_type "60.3x6.4"))
            (not (= taz_s_tmp_type "60.3x5.5"))
            (not (= taz_s_tmp_type "60.3x4.8"))
            (not (= taz_s_tmp_type "60.3x3.9"))
            (not (= taz_s_tmp_type "60.3x3.2"))
            (not (= taz_s_tmp_type "48.3x3.7"))
            (not (= taz_s_tmp_type "42.2x3.6"))
       )
       (progn (setq taz_s_tmp_type "508x12.7") (set_tile "taz_s_typ" "0"))
     )
    )
  )

  ;; ---------------------------
  ;; Reakcje na zmiane kategorii
  ;; ---------------------------
  (defun taz_s_on_category_change (/) 

    ;; Ustawienie kategorii na podstawie indeksu
    (if (= $value "0") (setq taz_s_tmp_category "Dwuteowniki"))
    (if (= $value "1") (setq taz_s_tmp_category "Ceowniki"))
    (if (= $value "2") (setq taz_s_tmp_category "Katowniki"))
    (if (= $value "3") (setq taz_s_tmp_category "Rury"))

    ;; Lista rodzin
    (start_list "taz_s_fam")

    (if (= taz_s_tmp_category "Dwuteowniki") 
      (progn 
        (add_list "HEA")
        (add_list "HEB")
        (add_list "IPE")
        (add_list "IPN")
      )
    )

    (if (= taz_s_tmp_category "Ceowniki") 
      (progn 
        (add_list "UPE")
        (add_list "UPN")
      )
    )

    (if (= taz_s_tmp_category "Katowniki") 
      (progn 
        (add_list "Katownik rownoramienny")
        (add_list "Katownik nierownoramienny")
      )
    )

    (if (= taz_s_tmp_category "Rury") 
      (progn 
        (add_list "Rura kwadratowa")
        (add_list "Rura prostokatna")
        (add_list "Rura okragla")
      )
    )

    (end_list)

    ;; Ustawienie domyslnej rodziny
    (if (= taz_s_tmp_category "Dwuteowniki") (setq taz_s_tmp_family "HEA"))
    (if (= taz_s_tmp_category "Ceowniki") (setq taz_s_tmp_family "UPE"))
    (if (= taz_s_tmp_category "Katowniki") 
      (setq taz_s_tmp_family "Katownik rownoramienny")
    )
    (if (= taz_s_tmp_category "Rury") (setq taz_s_tmp_family "Rura kwadratowa"))

    ;; Ustawienie indeksu rodziny na 0
    (set_tile "taz_s_fam" "0")

    ;; Start listy typow
    (start_list "taz_s_typ")

    ;; Dwuteowniki - HEA
    (if (= taz_s_tmp_family "HEA") 
      (progn 
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "400")
        (add_list "450")
        (add_list "500")
        (add_list "550")
        (add_list "600")
        (add_list "650")
        (add_list "700")
        (add_list "800")
        (add_list "900")
        (add_list "1000")
      )
    )

    ;; Dwuteowniki - HEB
    (if (= taz_s_tmp_family "HEB") 
      (progn 
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "400")
        (add_list "450")
        (add_list "500")
        (add_list "550")
        (add_list "600")
        (add_list "650")
        (add_list "700")
        (add_list "800")
        (add_list "900")
        (add_list "1000")
      )
    )

    ;; Dwuteowniki - IPE
    (if (= taz_s_tmp_family "IPE") 
      (progn 
        (add_list "80")
        (add_list "100")
        (add_list "120")
        (add_list "140")
        (add_list "160")
        (add_list "180")
        (add_list "200")
        (add_list "220")
        (add_list "240")
        (add_list "270")
        (add_list "300")
        (add_list "330")
        (add_list "360")
        (add_list "400")
        (add_list "450")
        (add_list "500")
        (add_list "550")
        (add_list "600")
        (add_list "750x137")
        (add_list "750x147")
        (add_list "750x173")
        (add_list "750x196")
      )
    )

    ;; Dwuteowniki - IPN
    (if (= taz_s_tmp_family "IPN") 
      (progn 
        (add_list "80")
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "380")
        (add_list "400")
        (add_list "450")
        (add_list "500")
        (add_list "550")
        (add_list "600")
      )
    )

    ;; Ceowniki – UPE
    (if (= taz_s_tmp_family "UPE") 
      (progn 
        (add_list "80")
        (add_list "100")
        (add_list "120")
        (add_list "140")
        (add_list "160")
        (add_list "180")
        (add_list "200")
        (add_list "220")
        (add_list "240")
        (add_list "270")
        (add_list "300")
        (add_list "330")
        (add_list "360")
        (add_list "400")
      )
    )

    ;; Ceowniki – UPN
    (if (= taz_s_tmp_family "UPN") 
      (progn 
        (add_list "50")
        (add_list "65")
        (add_list "80")
        (add_list "100")
        (add_list "120")
        (add_list "140")
        (add_list "160")
        (add_list "180")
        (add_list "200")
        (add_list "220")
        (add_list "240")
        (add_list "260")
        (add_list "280")
        (add_list "300")
        (add_list "320")
        (add_list "350")
        (add_list "380")
        (add_list "400")
      )
    )

    ;; Katowniki rownoramienne
    (if (= taz_s_tmp_family "Katownik rownoramienny") 
      (progn 
        (add_list "20x3")
        (add_list "25x3")
        (add_list "25x4")
        (add_list "30x3")
        (add_list "30x4")
        (add_list "30x5")
        (add_list "35x4")
        (add_list "35x5")
        (add_list "40x4")
        (add_list "40x5")
        (add_list "45x4")
        (add_list "45x5")
        (add_list "50x5")
        (add_list "50x6")
        (add_list "50x7")
        (add_list "55x6")
        (add_list "60x5")
        (add_list "60x6")
        (add_list "60x8")
        (add_list "65x7")
        (add_list "70x6")
        (add_list "70x7")
        (add_list "70x9")
        (add_list "75x7")
        (add_list "75x8")
        (add_list "80x6")
        (add_list "80x8")
        (add_list "80x10")
        (add_list "90x7")
        (add_list "90x8")
        (add_list "90x9")
        (add_list "100x8")
        (add_list "100x10")
        (add_list "100x12")
        (add_list "100x14")
        (add_list "110x10")
        (add_list "110x12")
        (add_list "120x10")
        (add_list "120x11")
        (add_list "120x12")
        (add_list "120x13")
        (add_list "120x15")
        (add_list "130x12")
        (add_list "140x10")
        (add_list "140x13")
        (add_list "140x15")
        (add_list "150x10")
        (add_list "150x12")
        (add_list "150x14")
        (add_list "150x15")
        (add_list "150x16")
        (add_list "150x18")
        (add_list "150x20")
        (add_list "160x15")
        (add_list "160x17")
        (add_list "160x19")
        (add_list "180x16")
        (add_list "180x18")
        (add_list "180x20")
        (add_list "180x22")
        (add_list "200x16")
        (add_list "200x18")
        (add_list "200x20")
        (add_list "200x22")
        (add_list "200x24")
        (add_list "200x26")
        (add_list "200x28")
        (add_list "200x30")
        (add_list "250x18")
        (add_list "250x20")
        (add_list "250x22")
        (add_list "250x24")
        (add_list "250x26")
        (add_list "250x28")
      )
    )

    ;; Katowniki nierownoramienne
    (if (= taz_s_tmp_family "Katownik nierownoramienny") 
      (progn 
        (add_list "30x20x3")
        (add_list "30x20x4")
        (add_list "40x20x3")
        (add_list "40x20x4")
        (add_list "40x25x4")
        (add_list "45x30x3")
        (add_list "45x30x4")
        (add_list "45x30x5")
        (add_list "50x30x4")
        (add_list "50x30x5")
        (add_list "50x40x4")
        (add_list "50x40x5")
        (add_list "60x30x5")
        (add_list "60x40x5")
        (add_list "60x40x6")
        (add_list "60x40x7")
        (add_list "65x50x5")
        (add_list "65x50x7")
        (add_list "65x50x9")
        (add_list "70x50x6")
        (add_list "75x50x7")
        (add_list "75x50x9")
        (add_list "75x55x5")
        (add_list "75x55x7")
        (add_list "75x55x9")
        (add_list "80x40x6")
        (add_list "80x40x8")
        (add_list "80x60x7")
        (add_list "80x65x8")
        (add_list "80x65x10")
        (add_list "90x60x6")
        (add_list "90x60x8")
        (add_list "100x50x6")
        (add_list "100x50x8")
        (add_list "100x50x10")
        (add_list "100x65x7")
        (add_list "100x65x9")
        (add_list "100x65x11")
        (add_list "100x75x7")
        (add_list "100x75x9")
        (add_list "100x75x11")
        (add_list "120x80x8")
        (add_list "120x80x10")
        (add_list "120x80x12")
        (add_list "120x80x14")
        (add_list "130x65x8")
        (add_list "130x65x10")
        (add_list "130x65x12")
        (add_list "130x90x12")
        (add_list "150x75x9")
        (add_list "150x75x11")
        (add_list "150x100x10")
        (add_list "150x100x12")
        (add_list "150x100x14")
        (add_list "160x80x12")
        (add_list "180x90x10")
        (add_list "180x90x12")
        (add_list "200x100x10")
        (add_list "200x100x12")
        (add_list "200x100x14")
        (add_list "200x100x16")
        (add_list "250x90x10")
        (add_list "250x90x12")
        (add_list "250x90x14")
        (add_list "250x90x16")
      )
    )

    ;; Rury - Rura kwadratowa (SHS)
    (if (= taz_s_tmp_family "Rura kwadratowa") 
      (progn 
        (add_list "38x38x2.5")
        (add_list "38x38x3")
        (add_list "38x38x3.5")
        (add_list "50x50x2.5")
        (add_list "50x50x3")
        (add_list "50x50x3.5")
        (add_list "50x50x4")
        (add_list "50x50x4.5")
        (add_list "60x60x2.5")
        (add_list "60x60x3")
        (add_list "60x60x3.5")
        (add_list "60x60x4")
        (add_list "60x60x4.5")
        (add_list "75x75x2.5")
        (add_list "75x75x3")
        (add_list "75x75x3.5")
        (add_list "75x75x4")
        (add_list "75x75x4.5")
        (add_list "75x75x5")
        (add_list "80x80x2.5")
        (add_list "80x80x3")
        (add_list "80x80x3.5")
        (add_list "80x80x4")
        (add_list "80x80x4.5")
        (add_list "80x80x5")
        (add_list "80x80x6")
        (add_list "100x100x2.5")
        (add_list "100x100x3")
        (add_list "100x100x3.5")
        (add_list "100x100x4")
        (add_list "100x100x4.5")
        (add_list "100x100x5")
        (add_list "100x100x6")
        (add_list "120x120x3")
        (add_list "120x120x3.5")
        (add_list "120x120x4")
        (add_list "120x120x4.5")
        (add_list "120x120x5")
        (add_list "120x120x6")
        (add_list "150x150x4")
        (add_list "150x150x4.5")
        (add_list "150x150x6")
        (add_list "150x150x8")
        (add_list "150x150x10")
        (add_list "175x175x4")
        (add_list "175x175x4.5")
        (add_list "175x175x6")
        (add_list "175x175x8")
        (add_list "175x175x10")
        (add_list "200x200x4.5")
        (add_list "200x200x6")
        (add_list "200x200x8")
        (add_list "200x200x10")
        (add_list "220x220x6")
        (add_list "220x220x8")
        (add_list "220x220x10")
        (add_list "250x250x4.5")
        (add_list "250x250x6")
        (add_list "250x250x8")
        (add_list "250x250x10")
        (add_list "285x285x8")
        (add_list "285x285x10")
      )
    )


    ;; Rury - Rura prostokatna (RHS)
    (if (= taz_s_tmp_family "Rura prostokatna") 
      (progn 
        (add_list "50x25x2.5")
        (add_list "50x25x3")
        (add_list "50x25x3.5")
        (add_list "60x40x2.5")
        (add_list "60x40x3")
        (add_list "60x40x3.5")
        (add_list "60x40x4")
        (add_list "60x40x4.5")
        (add_list "76x38x2.5")
        (add_list "76x38x3")
        (add_list "76x38x3.5")
        (add_list "76x38x4")
        (add_list "76x38x4.5")
        (add_list "80x40x2.5")
        (add_list "80x40x3")
        (add_list "80x40x3.5")
        (add_list "80x40x4")
        (add_list "80x40x4.5")
        (add_list "100x50x2.5")
        (add_list "100x50x3")
        (add_list "100x50x3.5")
        (add_list "100x50x4")
        (add_list "100x50x4.5")
        (add_list "100x50x5")
        (add_list "100x50x6")
        (add_list "120x60x3")
        (add_list "120x60x3.5")
        (add_list "120x60x4")
        (add_list "120x60x4.5")
        (add_list "120x60x5")
        (add_list "120x60x6")
        (add_list "150x100x3")
        (add_list "150x100x3.5")
        (add_list "150x100x4")
        (add_list "150x100x4.5")
        (add_list "150x100x5")
        (add_list "150x100x6")
        (add_list "160x80x3")
        (add_list "160x80x3.5")
        (add_list "160x80x4")
        (add_list "160x80x4.5")
        (add_list "160x80x5")
        (add_list "160x80x6")
        (add_list "200x100x4")
        (add_list "200x100x4.5")
        (add_list "200x100x6")
        (add_list "200x100x8")
        (add_list "200x100x10")
        (add_list "200x150x4")
        (add_list "200x150x4.5")
        (add_list "200x150x6")
        (add_list "200x150x8")
        (add_list "200x150x10")
        (add_list "250x100x4")
        (add_list "250x100x4.5")
        (add_list "250x100x6")
        (add_list "250x100x8")
        (add_list "250x100x10")
        (add_list "250x150x6")
        (add_list "250x150x8")
        (add_list "250x150x10")
        (add_list "300x140x6")
        (add_list "300x140x8")
        (add_list "300x140x10")
        (add_list "320x200x6")
        (add_list "320x200x8")
        (add_list "320x200x10")
        (add_list "340x180x6")
        (add_list "340x180x8")
        (add_list "340x180x10")
      )
    )


    ;; Rury - Rura okragla (CHS)
    (if (= taz_s_tmp_family "Rura okragla") 
      (progn 
        (add_list "508x12.7")
        (add_list "508x9.5")
        (add_list "457.2x12.7")
        (add_list "457.2x9.5")
        (add_list "406.4x12.7")
        (add_list "406.4x11.1")
        (add_list "406.4x9.5")
        (add_list "406.4x7.9")
        (add_list "355.6x12.7")
        (add_list "355.6x9.5")
        (add_list "355.6x7.9")
        (add_list "323.9x12.7")
        (add_list "323.9x9.5")
        (add_list "323.9x6.4")
        (add_list "317.5x15.9")
        (add_list "317.5x12.7")
        (add_list "317.5x9.5")
        (add_list "317.5x7.9")
        (add_list "317.5x6.4")
        (add_list "317.5x4.8")
        (add_list "312.8x15.9")
        (add_list "312.8x12.7")
        (add_list "312.8x9.5")
        (add_list "312.8x7.9")
        (add_list "312.8x6.4")
        (add_list "312.8x4.8")
        (add_list "311.2x15.9")
        (add_list "311.2x12.7")
        (add_list "311.2x9.5")
        (add_list "311.2x7.9")
        (add_list "311.2x6.4")
        (add_list "311.2x4.8")
        (add_list "285.8x15.9")
        (add_list "285.8x12.7")
        (add_list "285.8x9.5")
        (add_list "285.8x7.9")
        (add_list "285.8x6.4")
        (add_list "285.8x4.8")
        (add_list "273.1x12.7")
        (add_list "273.1x9.3")
        (add_list "273.1x6.4")
        (add_list "254x15.9")
        (add_list "254x12.7")
        (add_list "254x9.5")
        (add_list "254x7.9")
        (add_list "254x6.4")
        (add_list "254x4.8")
        (add_list "244.5x12.7")
        (add_list "244.5x9.5")
        (add_list "244.5x7.9")
        (add_list "244.5x6.4")
        (add_list "222.3x12.7")
        (add_list "222.3x9.5")
        (add_list "222.3x7.9")
        (add_list "222.3x6.4")
        (add_list "222.3x4.8")
        (add_list "219.1x12.7")
        (add_list "219.1x9.5")
        (add_list "219.1x8.2")
        (add_list "219.1x6.4")
        (add_list "219.1x4.8")
        (add_list "193.7x9.5")
        (add_list "193.7x8.3")
        (add_list "193.7x3.2")
        (add_list "190.5x12.7")
        (add_list "190.5x9.5")
        (add_list "190.5x7.9")
        (add_list "190.5x6.4")
        (add_list "190.5x4.8")
        (add_list "177.8x12.7")
        (add_list "177.8x9.5")
        (add_list "177.8x7.9")
        (add_list "177.8x6.4")
        (add_list "177.8x4.8")
        (add_list "177.8x3.2")
        (add_list "174.6x12.7")
        (add_list "174.6x9.5")
        (add_list "174.6x7.9")
        (add_list "174.6x6.4")
        (add_list "174.6x4.8")
        (add_list "168.3x12.7")
        (add_list "168.3x11")
        (add_list "168.3x9.5")
        (add_list "168.3x7.9")
        (add_list "168.3x7.1")
        (add_list "168.3x6.4")
        (add_list "168.3x4.8")
        (add_list "168.3x3.2")
        (add_list "155.6x12.7")
        (add_list "155.6x9.5")
        (add_list "155.6x7.9")
        (add_list "155.6x6.4")
        (add_list "155.6x4.8")
        (add_list "152.4x12.7")
        (add_list "152.4x9.5")
        (add_list "152.4x7.9")
        (add_list "152.4x7.1")
        (add_list "152.4x6.4")
        (add_list "152.4x4.8")
        (add_list "152.4x3.2")
        (add_list "141.3x9.5")
        (add_list "141.3x6.6")
        (add_list "141.3x4.8")
        (add_list "141.3x3.4")
        (add_list "139.7x12.7")
        (add_list "139.7x9.5")
        (add_list "139.7x6.6")
        (add_list "127x12.7")
        (add_list "127x9.5")
        (add_list "127x7.9")
        (add_list "127x6.6")
        (add_list "127x6.4")
        (add_list "127x4.8")
        (add_list "127x3.2")
        (add_list "114.3x8.6")
        (add_list "114.3x6")
        (add_list "114.3x4.8")
        (add_list "114.3x3.2")
        (add_list "101.6x8.6")
        (add_list "101.6x8")
        (add_list "101.6x6.4")
        (add_list "101.6x6")
        (add_list "101.6x5.7")
        (add_list "101.6x5.6")
        (add_list "101.6x4.8")
        (add_list "101.6x3.2")
        (add_list "88.9x8")
        (add_list "88.9x7.6")
        (add_list "88.9x6.4")
        (add_list "88.9x5.5")
        (add_list "88.9x5.2")
        (add_list "88.9x4.8")
        (add_list "88.9x3.2")
        (add_list "76.2x7.6")
        (add_list "76.2x6.4")
        (add_list "76.2x5.5")
        (add_list "76.2x5.2")
        (add_list "76.2x4.8")
        (add_list "76.2x3.9")
        (add_list "76.2x3.4")
        (add_list "76.2x3")
        (add_list "73x6.4")
        (add_list "73x5.2")
        (add_list "73x4.8")
        (add_list "73x3.2")
        (add_list "63.5x6.4")
        (add_list "63.5x4.8")
        (add_list "63.5x3.2")
        (add_list "60.3x6.4")
        (add_list "60.3x5.5")
        (add_list "60.3x4.8")
        (add_list "60.3x3.9")
        (add_list "60.3x3.2")
        (add_list "48.3x3.7")
        (add_list "42.2x3.6")
      )
    )

    (end_list)

    ;; Ustaw pierwszy typ recznie w zależnosci od rodziny

    (if (= taz_s_tmp_family "HEA") 
      (progn (setq taz_s_tmp_type "100") (set_tile "taz_s_typ" "0"))
    )

    (if (= taz_s_tmp_family "HEB") 
      (progn (setq taz_s_tmp_type "100") (set_tile "taz_s_typ" "0"))
    )

    (if (= taz_s_tmp_family "IPE") 
      (progn (setq taz_s_tmp_type "80") (set_tile "taz_s_typ" "0"))
    )

    (if (= taz_s_tmp_family "IPN") 
      (progn (setq taz_s_tmp_type "80") (set_tile "taz_s_typ" "0"))
    )

    (if (= taz_s_tmp_family "UPE") 
      (progn (setq taz_s_tmp_type "80") (set_tile "taz_s_typ" "0"))
    )

    (if (= taz_s_tmp_family "UPN") 
      (progn (setq taz_s_tmp_type "50") (set_tile "taz_s_typ" "0"))
    )

    (if (= taz_s_tmp_family "Katownik rownoramienny") 
      (progn (setq taz_s_tmp_type "20x3") (set_tile "taz_s_typ" "0"))
    )

    (if (= taz_s_tmp_family "Katownik nierownoramienny") 
      (progn (setq taz_s_tmp_type "30x20x3") (set_tile "taz_s_typ" "0"))
    )

    (if (= taz_s_tmp_family "Rura kwadratowa") 
      (progn (setq taz_s_tmp_type "38x38x2.5") (set_tile "taz_s_typ" "0"))
    )

    (if (= taz_s_tmp_family "Rura prostokatna") 
      (progn (setq taz_s_tmp_type "50x25x2.5") (set_tile "taz_s_typ" "0"))
    )

    (if (= taz_s_tmp_family "Rura okragla") 
      (progn (setq taz_s_tmp_type "508x12.7") (set_tile "taz_s_typ" "0"))
    )
  )

  (action_tile "taz_s_cat" "(taz_s_on_category_change)")

  ;; ---------------------------
  ;; Reakcje na zmiane rodziny
  ;; ---------------------------
  (defun taz_s_on_family_change (/) 

    ;; Mapowanie indeksu rodziny w zależnosci od kategorii
    (if (= (get_tile "taz_s_cat") "0") 
      (progn 
        (if (= $value "0") (setq taz_s_tmp_family "HEA"))
        (if (= $value "1") (setq taz_s_tmp_family "HEB"))
        (if (= $value "2") (setq taz_s_tmp_family "IPE"))
        (if (= $value "3") (setq taz_s_tmp_family "IPN"))
      )
    )

    (if (= (get_tile "taz_s_cat") "1") 
      (progn 
        (if (= $value "0") (setq taz_s_tmp_family "UPE"))
        (if (= $value "1") (setq taz_s_tmp_family "UPN"))
      )
    )

    (if (= (get_tile "taz_s_cat") "2") 
      (progn 
        (if (= $value "0") (setq taz_s_tmp_family "Katownik rownoramienny"))
        (if (= $value "1") (setq taz_s_tmp_family "Katownik nierownoramienny"))
      )
    )

    (if (= (get_tile "taz_s_cat") "3") 
      (progn 
        (if (= $value "0") (setq taz_s_tmp_family "Rura kwadratowa"))
        (if (= $value "1") (setq taz_s_tmp_family "Rura prostokatna"))
        (if (= $value "2") (setq taz_s_tmp_family "Rura okragla"))
      )
    )

    ;; Start listy typow
    (start_list "taz_s_typ")

    ;; Dwuteowniki - HEA
    (if (= taz_s_tmp_family "HEA") 
      (progn 
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "400")
        (add_list "450")
        (add_list "500")
        (add_list "550")
        (add_list "600")
        (add_list "650")
        (add_list "700")
        (add_list "800")
        (add_list "900")
        (add_list "1000")
      )
    )

    ;; Dwuteowniki - HEB
    (if (= taz_s_tmp_family "HEB") 
      (progn 
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "400")
        (add_list "450")
        (add_list "500")
        (add_list "550")
        (add_list "600")
        (add_list "650")
        (add_list "700")
        (add_list "800")
        (add_list "900")
        (add_list "1000")
      )
    )

    ;; Dwuteowniki - IPE
    (if (= taz_s_tmp_family "IPE") 
      (progn 
        (add_list "80")
        (add_list "100")
        (add_list "120")
        (add_list "140")
        (add_list "160")
        (add_list "180")
        (add_list "200")
        (add_list "220")
        (add_list "240")
        (add_list "270")
        (add_list "300")
        (add_list "330")
        (add_list "360")
        (add_list "400")
        (add_list "450")
        (add_list "500")
        (add_list "550")
        (add_list "600")
        (add_list "750x137")
        (add_list "750x147")
        (add_list "750x173")
        (add_list "750x196")
      )
    )

    ;; Dwuteowniki - IPN
    (if (= taz_s_tmp_family "IPN") 
      (progn 
        (add_list "80")
        (add_list "100")
        (add_list "120")
        (add_list "140")
        (add_list "160")
        (add_list "180")
        (add_list "200")
        (add_list "220")
        (add_list "240")
        (add_list "260")
        (add_list "280")
        (add_list "300")
        (add_list "320")
        (add_list "340")
        (add_list "360")
        (add_list "380")
        (add_list "400")
        (add_list "450")
        (add_list "500")
        (add_list "550")
        (add_list "600")
      )
    )

    ;; Ceowniki – UPE
    (if (= taz_s_tmp_family "UPE") 
      (progn 
        (add_list "80")
        (add_list "100")
        (add_list "120")
        (add_list "140")
        (add_list "160")
        (add_list "180")
        (add_list "200")
        (add_list "220")
        (add_list "240")
        (add_list "270")
        (add_list "300")
        (add_list "330")
        (add_list "360")
        (add_list "400")
      )
    )

    ;; Ceowniki – UPN
    (if (= taz_s_tmp_family "UPN") 
      (progn 
        (add_list "50")
        (add_list "65")
        (add_list "80")
        (add_list "100")
        (add_list "120")
        (add_list "140")
        (add_list "160")
        (add_list "180")
        (add_list "200")
        (add_list "220")
        (add_list "240")
        (add_list "260")
        (add_list "280")
        (add_list "300")
        (add_list "320")
        (add_list "350")
        (add_list "380")
        (add_list "400")
      )
    )

    ;; Katowniki rownoramienne
    (if (= taz_s_tmp_family "Katownik rownoramienny") 
      (progn 
        (add_list "20x3")
        (add_list "25x3")
        (add_list "25x4")
        (add_list "30x3")
        (add_list "30x4")
        (add_list "30x5")
        (add_list "35x4")
        (add_list "35x5")
        (add_list "40x4")
        (add_list "40x5")
        (add_list "45x4")
        (add_list "45x5")
        (add_list "50x5")
        (add_list "50x6")
        (add_list "50x7")
        (add_list "55x6")
        (add_list "60x5")
        (add_list "60x6")
        (add_list "60x8")
        (add_list "65x7")
        (add_list "70x6")
        (add_list "70x7")
        (add_list "70x9")
        (add_list "75x7")
        (add_list "75x8")
        (add_list "80x6")
        (add_list "80x8")
        (add_list "80x10")
        (add_list "90x7")
        (add_list "90x8")
        (add_list "90x9")
        (add_list "100x8")
        (add_list "100x10")
        (add_list "100x12")
        (add_list "100x14")
        (add_list "110x10")
        (add_list "110x12")
        (add_list "120x10")
        (add_list "120x11")
        (add_list "120x12")
        (add_list "120x13")
        (add_list "120x15")
        (add_list "130x12")
        (add_list "140x10")
        (add_list "140x13")
        (add_list "140x15")
        (add_list "150x10")
        (add_list "150x12")
        (add_list "150x14")
        (add_list "150x15")
        (add_list "150x16")
        (add_list "150x18")
        (add_list "150x20")
        (add_list "160x15")
        (add_list "160x17")
        (add_list "160x19")
        (add_list "180x16")
        (add_list "180x18")
        (add_list "180x20")
        (add_list "180x22")
        (add_list "200x16")
        (add_list "200x18")
        (add_list "200x20")
        (add_list "200x22")
        (add_list "200x24")
        (add_list "200x26")
        (add_list "200x28")
        (add_list "200x30")
        (add_list "250x18")
        (add_list "250x20")
        (add_list "250x22")
        (add_list "250x24")
        (add_list "250x26")
        (add_list "250x28")
      )
    )

    ;; Katowniki nierownoramienne
    (if (= taz_s_tmp_family "Katownik nierownoramienny") 
      (progn 
        (add_list "30x20x3")
        (add_list "30x20x4")
        (add_list "40x20x3")
        (add_list "40x20x4")
        (add_list "40x25x4")
        (add_list "45x30x3")
        (add_list "45x30x4")
        (add_list "45x30x5")
        (add_list "50x30x4")
        (add_list "50x30x5")
        (add_list "50x40x4")
        (add_list "50x40x5")
        (add_list "60x30x5")
        (add_list "60x40x5")
        (add_list "60x40x6")
        (add_list "60x40x7")
        (add_list "65x50x5")
        (add_list "65x50x7")
        (add_list "65x50x9")
        (add_list "70x50x6")
        (add_list "75x50x7")
        (add_list "75x50x9")
        (add_list "75x55x5")
        (add_list "75x55x7")
        (add_list "75x55x9")
        (add_list "80x40x6")
        (add_list "80x40x8")
        (add_list "80x60x7")
        (add_list "80x65x8")
        (add_list "80x65x10")
        (add_list "90x60x6")
        (add_list "90x60x8")
        (add_list "100x50x6")
        (add_list "100x50x8")
        (add_list "100x50x10")
        (add_list "100x65x7")
        (add_list "100x65x9")
        (add_list "100x65x11")
        (add_list "100x75x7")
        (add_list "100x75x9")
        (add_list "100x75x11")
        (add_list "120x80x8")
        (add_list "120x80x10")
        (add_list "120x80x12")
        (add_list "120x80x14")
        (add_list "130x65x8")
        (add_list "130x65x10")
        (add_list "130x65x12")
        (add_list "130x90x12")
        (add_list "150x75x9")
        (add_list "150x75x11")
        (add_list "150x100x10")
        (add_list "150x100x12")
        (add_list "150x100x14")
        (add_list "160x80x12")
        (add_list "180x90x10")
        (add_list "180x90x12")
        (add_list "200x100x10")
        (add_list "200x100x12")
        (add_list "200x100x14")
        (add_list "200x100x16")
        (add_list "250x90x10")
        (add_list "250x90x12")
        (add_list "250x90x14")
        (add_list "250x90x16")
      )
    )

    ;; Rury - Rura kwadratowa (SHS)
    (if (= taz_s_tmp_family "Rura kwadratowa") 
      (progn 
        (add_list "38x38x2.5")
        (add_list "38x38x3")
        (add_list "38x38x3.5")
        (add_list "50x50x2.5")
        (add_list "50x50x3")
        (add_list "50x50x3.5")
        (add_list "50x50x4")
        (add_list "50x50x4.5")
        (add_list "60x60x2.5")
        (add_list "60x60x3")
        (add_list "60x60x3.5")
        (add_list "60x60x4")
        (add_list "60x60x4.5")
        (add_list "75x75x2.5")
        (add_list "75x75x3")
        (add_list "75x75x3.5")
        (add_list "75x75x4")
        (add_list "75x75x4.5")
        (add_list "75x75x5")
        (add_list "80x80x2.5")
        (add_list "80x80x3")
        (add_list "80x80x3.5")
        (add_list "80x80x4")
        (add_list "80x80x4.5")
        (add_list "80x80x5")
        (add_list "80x80x6")
        (add_list "100x100x2.5")
        (add_list "100x100x3")
        (add_list "100x100x3.5")
        (add_list "100x100x4")
        (add_list "100x100x4.5")
        (add_list "100x100x5")
        (add_list "100x100x6")
        (add_list "120x120x3")
        (add_list "120x120x3.5")
        (add_list "120x120x4")
        (add_list "120x120x4.5")
        (add_list "120x120x5")
        (add_list "120x120x6")
        (add_list "150x150x4")
        (add_list "150x150x4.5")
        (add_list "150x150x6")
        (add_list "150x150x8")
        (add_list "150x150x10")
        (add_list "175x175x4")
        (add_list "175x175x4.5")
        (add_list "175x175x6")
        (add_list "175x175x8")
        (add_list "175x175x10")
        (add_list "200x200x4.5")
        (add_list "200x200x6")
        (add_list "200x200x8")
        (add_list "200x200x10")
        (add_list "220x220x6")
        (add_list "220x220x8")
        (add_list "220x220x10")
        (add_list "250x250x4.5")
        (add_list "250x250x6")
        (add_list "250x250x8")
        (add_list "250x250x10")
        (add_list "285x285x8")
        (add_list "285x285x10")
      )
    )

    ;; Rury - Rura prostokatna (RHS)
    (if (= taz_s_tmp_family "Rura prostokatna") 
      (progn 
        (add_list "50x25x2.5")
        (add_list "50x25x3")
        (add_list "50x25x3.5")
        (add_list "60x40x2.5")
        (add_list "60x40x3")
        (add_list "60x40x3.5")
        (add_list "60x40x4")
        (add_list "60x40x4.5")
        (add_list "76x38x2.5")
        (add_list "76x38x3")
        (add_list "76x38x3.5")
        (add_list "76x38x4")
        (add_list "76x38x4.5")
        (add_list "80x40x2.5")
        (add_list "80x40x3")
        (add_list "80x40x3.5")
        (add_list "80x40x4")
        (add_list "80x40x4.5")
        (add_list "100x50x2.5")
        (add_list "100x50x3")
        (add_list "100x50x3.5")
        (add_list "100x50x4")
        (add_list "100x50x4.5")
        (add_list "100x50x5")
        (add_list "100x50x6")
        (add_list "120x60x3")
        (add_list "120x60x3.5")
        (add_list "120x60x4")
        (add_list "120x60x4.5")
        (add_list "120x60x5")
        (add_list "120x60x6")
        (add_list "150x100x3")
        (add_list "150x100x3.5")
        (add_list "150x100x4")
        (add_list "150x100x4.5")
        (add_list "150x100x5")
        (add_list "150x100x6")
        (add_list "160x80x3")
        (add_list "160x80x3.5")
        (add_list "160x80x4")
        (add_list "160x80x4.5")
        (add_list "160x80x5")
        (add_list "160x80x6")
        (add_list "200x100x4")
        (add_list "200x100x4.5")
        (add_list "200x100x6")
        (add_list "200x100x8")
        (add_list "200x100x10")
        (add_list "200x150x4")
        (add_list "200x150x4.5")
        (add_list "200x150x6")
        (add_list "200x150x8")
        (add_list "200x150x10")
        (add_list "250x100x4")
        (add_list "250x100x4.5")
        (add_list "250x100x6")
        (add_list "250x100x8")
        (add_list "250x100x10")
        (add_list "250x150x6")
        (add_list "250x150x8")
        (add_list "250x150x10")
        (add_list "300x140x6")
        (add_list "300x140x8")
        (add_list "300x140x10")
        (add_list "320x200x6")
        (add_list "320x200x8")
        (add_list "320x200x10")
        (add_list "340x180x6")
        (add_list "340x180x8")
        (add_list "340x180x10")
      )
    )

    ;; Rury - Rura okragla (CHS)
    (if (= taz_s_tmp_family "Rura okragla") 
      (progn 
        (add_list "508x12.7")
        (add_list "508x9.5")
        (add_list "457.2x12.7")
        (add_list "457.2x9.5")
        (add_list "406.4x12.7")
        (add_list "406.4x11.1")
        (add_list "406.4x9.5")
        (add_list "406.4x7.9")
        (add_list "355.6x12.7")
        (add_list "355.6x9.5")
        (add_list "355.6x7.9")
        (add_list "323.9x12.7")
        (add_list "323.9x9.5")
        (add_list "323.9x6.4")
        (add_list "317.5x15.9")
        (add_list "317.5x12.7")
        (add_list "317.5x9.5")
        (add_list "317.5x7.9")
        (add_list "317.5x6.4")
        (add_list "317.5x4.8")
        (add_list "312.8x15.9")
        (add_list "312.8x12.7")
        (add_list "312.8x9.5")
        (add_list "312.8x7.9")
        (add_list "312.8x6.4")
        (add_list "312.8x4.8")
        (add_list "311.2x15.9")
        (add_list "311.2x12.7")
        (add_list "311.2x9.5")
        (add_list "311.2x7.9")
        (add_list "311.2x6.4")
        (add_list "311.2x4.8")
        (add_list "285.8x15.9")
        (add_list "285.8x12.7")
        (add_list "285.8x9.5")
        (add_list "285.8x7.9")
        (add_list "285.8x6.4")
        (add_list "285.8x4.8")
        (add_list "273.1x12.7")
        (add_list "273.1x9.3")
        (add_list "273.1x6.4")
        (add_list "254x15.9")
        (add_list "254x12.7")
        (add_list "254x9.5")
        (add_list "254x7.9")
        (add_list "254x6.4")
        (add_list "254x4.8")
        (add_list "244.5x12.7")
        (add_list "244.5x9.5")
        (add_list "244.5x7.9")
        (add_list "244.5x6.4")
        (add_list "222.3x12.7")
        (add_list "222.3x9.5")
        (add_list "222.3x7.9")
        (add_list "222.3x6.4")
        (add_list "222.3x4.8")
        (add_list "219.1x12.7")
        (add_list "219.1x9.5")
        (add_list "219.1x8.2")
        (add_list "219.1x6.4")
        (add_list "219.1x4.8")
        (add_list "193.7x9.5")
        (add_list "193.7x8.3")
        (add_list "193.7x3.2")
        (add_list "190.5x12.7")
        (add_list "190.5x9.5")
        (add_list "190.5x7.9")
        (add_list "190.5x6.4")
        (add_list "190.5x4.8")
        (add_list "177.8x12.7")
        (add_list "177.8x9.5")
        (add_list "177.8x7.9")
        (add_list "177.8x6.4")
        (add_list "177.8x4.8")
        (add_list "177.8x3.2")
        (add_list "174.6x12.7")
        (add_list "174.6x9.5")
        (add_list "174.6x7.9")
        (add_list "174.6x6.4")
        (add_list "174.6x4.8")
        (add_list "168.3x12.7")
        (add_list "168.3x11")
        (add_list "168.3x9.5")
        (add_list "168.3x7.9")
        (add_list "168.3x7.1")
        (add_list "168.3x6.4")
        (add_list "168.3x4.8")
        (add_list "168.3x3.2")
        (add_list "155.6x12.7")
        (add_list "155.6x9.5")
        (add_list "155.6x7.9")
        (add_list "155.6x6.4")
        (add_list "155.6x4.8")
        (add_list "152.4x12.7")
        (add_list "152.4x9.5")
        (add_list "152.4x7.9")
        (add_list "152.4x7.1")
        (add_list "152.4x6.4")
        (add_list "152.4x4.8")
        (add_list "152.4x3.2")
        (add_list "141.3x9.5")
        (add_list "141.3x6.6")
        (add_list "141.3x4.8")
        (add_list "141.3x3.4")
        (add_list "139.7x12.7")
        (add_list "139.7x9.5")
        (add_list "139.7x6.6")
        (add_list "127x12.7")
        (add_list "127x9.5")
        (add_list "127x7.9")
        (add_list "127x6.6")
        (add_list "127x6.4")
        (add_list "127x4.8")
        (add_list "127x3.2")
        (add_list "114.3x8.6")
        (add_list "114.3x6")
        (add_list "114.3x4.8")
        (add_list "114.3x3.2")
        (add_list "101.6x8.6")
        (add_list "101.6x8")
        (add_list "101.6x6.4")
        (add_list "101.6x6")
        (add_list "101.6x5.7")
        (add_list "101.6x5.6")
        (add_list "101.6x4.8")
        (add_list "101.6x3.2")
        (add_list "88.9x8")
        (add_list "88.9x7.6")
        (add_list "88.9x6.4")
        (add_list "88.9x5.5")
        (add_list "88.9x5.2")
        (add_list "88.9x4.8")
        (add_list "88.9x3.2")
        (add_list "76.2x7.6")
        (add_list "76.2x6.4")
        (add_list "76.2x5.5")
        (add_list "76.2x5.2")
        (add_list "76.2x4.8")
        (add_list "76.2x3.9")
        (add_list "76.2x3.4")
        (add_list "76.2x3")
        (add_list "73x6.4")
        (add_list "73x5.2")
        (add_list "73x4.8")
        (add_list "73x3.2")
        (add_list "63.5x6.4")
        (add_list "63.5x4.8")
        (add_list "63.5x3.2")
        (add_list "60.3x6.4")
        (add_list "60.3x5.5")
        (add_list "60.3x4.8")
        (add_list "60.3x3.9")
        (add_list "60.3x3.2")
        (add_list "48.3x3.7")
        (add_list "42.2x3.6")
      )
    )

    (end_list)

    ;; Ustaw pierwszy typ recznie w zależnosci od rodziny

    (if (= taz_s_tmp_family "HEA") 
      (progn (setq taz_s_tmp_type "100") (set_tile "taz_s_typ" "0"))
    )

    (if (= taz_s_tmp_family "HEB") 
      (progn (setq taz_s_tmp_type "100") (set_tile "taz_s_typ" "0"))
    )

    (if (= taz_s_tmp_family "IPE") 
      (progn (setq taz_s_tmp_type "80") (set_tile "taz_s_typ" "0"))
    )

    (if (= taz_s_tmp_family "IPN") 
      (progn (setq taz_s_tmp_type "80") (set_tile "taz_s_typ" "0"))
    )

    (if (= taz_s_tmp_family "UPE") 
      (progn (setq taz_s_tmp_type "80") (set_tile "taz_s_typ" "0"))
    )

    (if (= taz_s_tmp_family "UPN") 
      (progn (setq taz_s_tmp_type "50") (set_tile "taz_s_typ" "0"))
    )

    (if (= taz_s_tmp_family "Katownik rownoramienny") 
      (progn (setq taz_s_tmp_type "20x3") (set_tile "taz_s_typ" "0"))
    )

    (if (= taz_s_tmp_family "Katownik nierownoramienny") 
      (progn (setq taz_s_tmp_type "30x20x3") (set_tile "taz_s_typ" "0"))
    )

    (if (= taz_s_tmp_family "Rura kwadratowa") 
      (progn (setq taz_s_tmp_type "38x38x2.5") (set_tile "taz_s_typ" "0"))
    )

    (if (= taz_s_tmp_family "Rura prostokatna") 
      (progn (setq taz_s_tmp_type "50x25x2.5") (set_tile "taz_s_typ" "0"))
    )

    (if (= taz_s_tmp_family "Rura okragla") 
      (progn (setq taz_s_tmp_type "508x12.7") (set_tile "taz_s_typ" "0"))
    )
  )

  (action_tile "taz_s_fam" "(taz_s_on_family_change)")

  ;; ---------------------------
  ;; Reakcje na zmiane typu
  ;; ---------------------------
  (defun taz_s_on_type_change (/) 

    ;; Dwuteowniki - HEA
    (if (= taz_s_tmp_family "HEA") 
      (progn 
        (if (= $value "0") (setq taz_s_tmp_type "100"))
        (if (= $value "1") (setq taz_s_tmp_type "120"))
        (if (= $value "2") (setq taz_s_tmp_type "140"))
        (if (= $value "3") (setq taz_s_tmp_type "160"))
        (if (= $value "4") (setq taz_s_tmp_type "180"))
        (if (= $value "5") (setq taz_s_tmp_type "200"))
        (if (= $value "6") (setq taz_s_tmp_type "220"))
        (if (= $value "7") (setq taz_s_tmp_type "240"))
        (if (= $value "8") (setq taz_s_tmp_type "260"))
        (if (= $value "9") (setq taz_s_tmp_type "280"))
        (if (= $value "10") (setq taz_s_tmp_type "300"))
        (if (= $value "11") (setq taz_s_tmp_type "320"))
        (if (= $value "12") (setq taz_s_tmp_type "340"))
        (if (= $value "13") (setq taz_s_tmp_type "360"))
        (if (= $value "14") (setq taz_s_tmp_type "400"))
        (if (= $value "15") (setq taz_s_tmp_type "450"))
        (if (= $value "16") (setq taz_s_tmp_type "500"))
        (if (= $value "17") (setq taz_s_tmp_type "550"))
        (if (= $value "18") (setq taz_s_tmp_type "600"))
        (if (= $value "19") (setq taz_s_tmp_type "650"))
        (if (= $value "20") (setq taz_s_tmp_type "700"))
        (if (= $value "21") (setq taz_s_tmp_type "800"))
        (if (= $value "22") (setq taz_s_tmp_type "900"))
        (if (= $value "23") (setq taz_s_tmp_type "1000"))
      )
    )

    ;; Dwuteowniki - HEB
    (if (= taz_s_tmp_family "HEB") 
      (progn 
        (if (= $value "0") (setq taz_s_tmp_type "100"))
        (if (= $value "1") (setq taz_s_tmp_type "120"))
        (if (= $value "2") (setq taz_s_tmp_type "140"))
        (if (= $value "3") (setq taz_s_tmp_type "160"))
        (if (= $value "4") (setq taz_s_tmp_type "180"))
        (if (= $value "5") (setq taz_s_tmp_type "200"))
        (if (= $value "6") (setq taz_s_tmp_type "220"))
        (if (= $value "7") (setq taz_s_tmp_type "240"))
        (if (= $value "8") (setq taz_s_tmp_type "260"))
        (if (= $value "9") (setq taz_s_tmp_type "280"))
        (if (= $value "10") (setq taz_s_tmp_type "300"))
        (if (= $value "11") (setq taz_s_tmp_type "320"))
        (if (= $value "12") (setq taz_s_tmp_type "340"))
        (if (= $value "13") (setq taz_s_tmp_type "360"))
        (if (= $value "14") (setq taz_s_tmp_type "400"))
        (if (= $value "15") (setq taz_s_tmp_type "450"))
        (if (= $value "16") (setq taz_s_tmp_type "500"))
        (if (= $value "17") (setq taz_s_tmp_type "550"))
        (if (= $value "18") (setq taz_s_tmp_type "600"))
        (if (= $value "19") (setq taz_s_tmp_type "650"))
        (if (= $value "20") (setq taz_s_tmp_type "700"))
        (if (= $value "21") (setq taz_s_tmp_type "800"))
        (if (= $value "22") (setq taz_s_tmp_type "900"))
        (if (= $value "23") (setq taz_s_tmp_type "1000"))
      )
    )

    ;; Dwuteowniki - IPE
    (if (= taz_s_tmp_family "IPE") 
      (progn 
        (if (= $value "0") (setq taz_s_tmp_type "80"))
        (if (= $value "1") (setq taz_s_tmp_type "100"))
        (if (= $value "2") (setq taz_s_tmp_type "120"))
        (if (= $value "3") (setq taz_s_tmp_type "140"))
        (if (= $value "4") (setq taz_s_tmp_type "160"))
        (if (= $value "5") (setq taz_s_tmp_type "180"))
        (if (= $value "6") (setq taz_s_tmp_type "200"))
        (if (= $value "7") (setq taz_s_tmp_type "220"))
        (if (= $value "8") (setq taz_s_tmp_type "240"))
        (if (= $value "9") (setq taz_s_tmp_type "270"))
        (if (= $value "10") (setq taz_s_tmp_type "300"))
        (if (= $value "11") (setq taz_s_tmp_type "330"))
        (if (= $value "12") (setq taz_s_tmp_type "360"))
        (if (= $value "13") (setq taz_s_tmp_type "400"))
        (if (= $value "14") (setq taz_s_tmp_type "450"))
        (if (= $value "15") (setq taz_s_tmp_type "500"))
        (if (= $value "16") (setq taz_s_tmp_type "550"))
        (if (= $value "17") (setq taz_s_tmp_type "600"))
        (if (= $value "18") (setq taz_s_tmp_type "750x137"))
        (if (= $value "19") (setq taz_s_tmp_type "750x147"))
        (if (= $value "20") (setq taz_s_tmp_type "750x173"))
        (if (= $value "21") (setq taz_s_tmp_type "750x196"))
      )
    )

    ;; Dwuteowniki - IPN
    (if (= taz_s_tmp_family "IPN") 
      (progn 
        (if (= $value "0") (setq taz_s_tmp_type "80"))
        (if (= $value "1") (setq taz_s_tmp_type "100"))
        (if (= $value "2") (setq taz_s_tmp_type "120"))
        (if (= $value "3") (setq taz_s_tmp_type "140"))
        (if (= $value "4") (setq taz_s_tmp_type "160"))
        (if (= $value "5") (setq taz_s_tmp_type "180"))
        (if (= $value "6") (setq taz_s_tmp_type "200"))
        (if (= $value "7") (setq taz_s_tmp_type "220"))
        (if (= $value "8") (setq taz_s_tmp_type "240"))
        (if (= $value "9") (setq taz_s_tmp_type "260"))
        (if (= $value "10") (setq taz_s_tmp_type "280"))
        (if (= $value "11") (setq taz_s_tmp_type "300"))
        (if (= $value "12") (setq taz_s_tmp_type "320"))
        (if (= $value "13") (setq taz_s_tmp_type "340"))
        (if (= $value "14") (setq taz_s_tmp_type "360"))
        (if (= $value "15") (setq taz_s_tmp_type "380"))
        (if (= $value "16") (setq taz_s_tmp_type "400"))
        (if (= $value "17") (setq taz_s_tmp_type "450"))
        (if (= $value "18") (setq taz_s_tmp_type "500"))
        (if (= $value "19") (setq taz_s_tmp_type "550"))
        (if (= $value "20") (setq taz_s_tmp_type "600"))
      )
    )

    ;; Ceowniki – UPE
    (if (= taz_s_tmp_family "UPE") 
      (progn 
        (if (= $value "0") (setq taz_s_tmp_type "80"))
        (if (= $value "1") (setq taz_s_tmp_type "100"))
        (if (= $value "2") (setq taz_s_tmp_type "120"))
        (if (= $value "3") (setq taz_s_tmp_type "140"))
        (if (= $value "4") (setq taz_s_tmp_type "160"))
        (if (= $value "5") (setq taz_s_tmp_type "180"))
        (if (= $value "6") (setq taz_s_tmp_type "200"))
        (if (= $value "7") (setq taz_s_tmp_type "220"))
        (if (= $value "8") (setq taz_s_tmp_type "240"))
        (if (= $value "9") (setq taz_s_tmp_type "270"))
        (if (= $value "10") (setq taz_s_tmp_type "300"))
        (if (= $value "11") (setq taz_s_tmp_type "330"))
        (if (= $value "12") (setq taz_s_tmp_type "360"))
        (if (= $value "13") (setq taz_s_tmp_type "400"))
      )
    )

    ;; Ceowniki – UPN
    (if (= taz_s_tmp_family "UPN") 
      (progn 
        (if (= $value "0") (setq taz_s_tmp_type "50"))
        (if (= $value "1") (setq taz_s_tmp_type "65"))
        (if (= $value "2") (setq taz_s_tmp_type "80"))
        (if (= $value "3") (setq taz_s_tmp_type "100"))
        (if (= $value "4") (setq taz_s_tmp_type "120"))
        (if (= $value "5") (setq taz_s_tmp_type "140"))
        (if (= $value "6") (setq taz_s_tmp_type "160"))
        (if (= $value "7") (setq taz_s_tmp_type "180"))
        (if (= $value "8") (setq taz_s_tmp_type "200"))
        (if (= $value "9") (setq taz_s_tmp_type "220"))
        (if (= $value "10") (setq taz_s_tmp_type "240"))
        (if (= $value "11") (setq taz_s_tmp_type "260"))
        (if (= $value "12") (setq taz_s_tmp_type "280"))
        (if (= $value "13") (setq taz_s_tmp_type "300"))
        (if (= $value "14") (setq taz_s_tmp_type "320"))
        (if (= $value "15") (setq taz_s_tmp_type "350"))
        (if (= $value "16") (setq taz_s_tmp_type "380"))
        (if (= $value "17") (setq taz_s_tmp_type "400"))
      )
    )

    ;; Katowniki rownoramienne
    (if (= taz_s_tmp_family "Katownik rownoramienny") 
      (progn 
        (if (= $value "0") (setq taz_s_tmp_type "20x3"))
        (if (= $value "1") (setq taz_s_tmp_type "25x3"))
        (if (= $value "2") (setq taz_s_tmp_type "25x4"))
        (if (= $value "3") (setq taz_s_tmp_type "30x3"))
        (if (= $value "4") (setq taz_s_tmp_type "30x4"))
        (if (= $value "5") (setq taz_s_tmp_type "30x5"))
        (if (= $value "6") (setq taz_s_tmp_type "35x4"))
        (if (= $value "7") (setq taz_s_tmp_type "35x5"))
        (if (= $value "8") (setq taz_s_tmp_type "40x4"))
        (if (= $value "9") (setq taz_s_tmp_type "40x5"))
        (if (= $value "10") (setq taz_s_tmp_type "45x4"))
        (if (= $value "11") (setq taz_s_tmp_type "45x5"))
        (if (= $value "12") (setq taz_s_tmp_type "50x5"))
        (if (= $value "13") (setq taz_s_tmp_type "50x6"))
        (if (= $value "14") (setq taz_s_tmp_type "50x7"))
        (if (= $value "15") (setq taz_s_tmp_type "55x6"))
        (if (= $value "16") (setq taz_s_tmp_type "60x5"))
        (if (= $value "17") (setq taz_s_tmp_type "60x6"))
        (if (= $value "18") (setq taz_s_tmp_type "60x8"))
        (if (= $value "19") (setq taz_s_tmp_type "65x7"))
        (if (= $value "20") (setq taz_s_tmp_type "70x6"))
        (if (= $value "21") (setq taz_s_tmp_type "70x7"))
        (if (= $value "22") (setq taz_s_tmp_type "70x9"))
        (if (= $value "23") (setq taz_s_tmp_type "75x7"))
        (if (= $value "24") (setq taz_s_tmp_type "75x8"))
        (if (= $value "25") (setq taz_s_tmp_type "80x6"))
        (if (= $value "26") (setq taz_s_tmp_type "80x8"))
        (if (= $value "27") (setq taz_s_tmp_type "80x10"))
        (if (= $value "28") (setq taz_s_tmp_type "90x7"))
        (if (= $value "29") (setq taz_s_tmp_type "90x8"))
        (if (= $value "30") (setq taz_s_tmp_type "90x9"))
        (if (= $value "31") (setq taz_s_tmp_type "100x8"))
        (if (= $value "32") (setq taz_s_tmp_type "100x10"))
        (if (= $value "33") (setq taz_s_tmp_type "100x12"))
        (if (= $value "34") (setq taz_s_tmp_type "100x14"))
        (if (= $value "35") (setq taz_s_tmp_type "110x10"))
        (if (= $value "36") (setq taz_s_tmp_type "110x12"))
        (if (= $value "37") (setq taz_s_tmp_type "120x10"))
        (if (= $value "38") (setq taz_s_tmp_type "120x11"))
        (if (= $value "39") (setq taz_s_tmp_type "120x12"))
        (if (= $value "40") (setq taz_s_tmp_type "120x13"))
        (if (= $value "41") (setq taz_s_tmp_type "120x15"))
        (if (= $value "42") (setq taz_s_tmp_type "130x12"))
        (if (= $value "43") (setq taz_s_tmp_type "140x10"))
        (if (= $value "44") (setq taz_s_tmp_type "140x13"))
        (if (= $value "45") (setq taz_s_tmp_type "140x15"))
        (if (= $value "46") (setq taz_s_tmp_type "150x10"))
        (if (= $value "47") (setq taz_s_tmp_type "150x12"))
        (if (= $value "48") (setq taz_s_tmp_type "150x14"))
        (if (= $value "49") (setq taz_s_tmp_type "150x15"))
        (if (= $value "50") (setq taz_s_tmp_type "150x16"))
        (if (= $value "51") (setq taz_s_tmp_type "150x18"))
        (if (= $value "52") (setq taz_s_tmp_type "150x20"))
        (if (= $value "53") (setq taz_s_tmp_type "160x15"))
        (if (= $value "54") (setq taz_s_tmp_type "160x17"))
        (if (= $value "55") (setq taz_s_tmp_type "160x19"))
        (if (= $value "56") (setq taz_s_tmp_type "180x16"))
        (if (= $value "57") (setq taz_s_tmp_type "180x18"))
        (if (= $value "58") (setq taz_s_tmp_type "180x20"))
        (if (= $value "59") (setq taz_s_tmp_type "180x22"))
        (if (= $value "60") (setq taz_s_tmp_type "200x16"))
        (if (= $value "61") (setq taz_s_tmp_type "200x18"))
        (if (= $value "62") (setq taz_s_tmp_type "200x20"))
        (if (= $value "63") (setq taz_s_tmp_type "200x22"))
        (if (= $value "64") (setq taz_s_tmp_type "200x24"))
        (if (= $value "65") (setq taz_s_tmp_type "200x26"))
        (if (= $value "66") (setq taz_s_tmp_type "200x28"))
        (if (= $value "67") (setq taz_s_tmp_type "200x30"))
        (if (= $value "68") (setq taz_s_tmp_type "250x18"))
        (if (= $value "69") (setq taz_s_tmp_type "250x20"))
        (if (= $value "70") (setq taz_s_tmp_type "250x22"))
        (if (= $value "71") (setq taz_s_tmp_type "250x24"))
        (if (= $value "72") (setq taz_s_tmp_type "250x26"))
        (if (= $value "73") (setq taz_s_tmp_type "250x28"))
      )
    )

    ;; Katowniki nierownoramienne
    (if (= taz_s_tmp_family "Katownik nierownoramienny") 
      (progn 
        (if (= $value "0") (setq taz_s_tmp_type "30x20x3"))
        (if (= $value "1") (setq taz_s_tmp_type "30x20x4"))
        (if (= $value "2") (setq taz_s_tmp_type "40x20x3"))
        (if (= $value "3") (setq taz_s_tmp_type "40x20x4"))
        (if (= $value "4") (setq taz_s_tmp_type "40x25x4"))
        (if (= $value "5") (setq taz_s_tmp_type "45x30x3"))
        (if (= $value "6") (setq taz_s_tmp_type "45x30x4"))
        (if (= $value "7") (setq taz_s_tmp_type "45x30x5"))
        (if (= $value "8") (setq taz_s_tmp_type "50x30x4"))
        (if (= $value "9") (setq taz_s_tmp_type "50x30x5"))
        (if (= $value "10") (setq taz_s_tmp_type "50x40x4"))
        (if (= $value "11") (setq taz_s_tmp_type "50x40x5"))
        (if (= $value "12") (setq taz_s_tmp_type "60x30x5"))
        (if (= $value "13") (setq taz_s_tmp_type "60x40x5"))
        (if (= $value "14") (setq taz_s_tmp_type "60x40x6"))
        (if (= $value "15") (setq taz_s_tmp_type "60x40x7"))
        (if (= $value "16") (setq taz_s_tmp_type "65x50x5"))
        (if (= $value "17") (setq taz_s_tmp_type "65x50x7"))
        (if (= $value "18") (setq taz_s_tmp_type "65x50x9"))
        (if (= $value "19") (setq taz_s_tmp_type "70x50x6"))
        (if (= $value "20") (setq taz_s_tmp_type "75x50x7"))
        (if (= $value "21") (setq taz_s_tmp_type "75x50x9"))
        (if (= $value "22") (setq taz_s_tmp_type "75x55x5"))
        (if (= $value "23") (setq taz_s_tmp_type "75x55x7"))
        (if (= $value "24") (setq taz_s_tmp_type "75x55x9"))
        (if (= $value "25") (setq taz_s_tmp_type "80x40x6"))
        (if (= $value "26") (setq taz_s_tmp_type "80x40x8"))
        (if (= $value "27") (setq taz_s_tmp_type "80x60x7"))
        (if (= $value "28") (setq taz_s_tmp_type "80x65x8"))
        (if (= $value "29") (setq taz_s_tmp_type "80x65x10"))
        (if (= $value "30") (setq taz_s_tmp_type "90x60x6"))
        (if (= $value "31") (setq taz_s_tmp_type "90x60x8"))
        (if (= $value "32") (setq taz_s_tmp_type "100x50x6"))
        (if (= $value "33") (setq taz_s_tmp_type "100x50x8"))
        (if (= $value "34") (setq taz_s_tmp_type "100x50x10"))
        (if (= $value "35") (setq taz_s_tmp_type "100x65x7"))
        (if (= $value "36") (setq taz_s_tmp_type "100x65x9"))
        (if (= $value "37") (setq taz_s_tmp_type "100x65x11"))
        (if (= $value "38") (setq taz_s_tmp_type "100x75x7"))
        (if (= $value "39") (setq taz_s_tmp_type "100x75x9"))
        (if (= $value "40") (setq taz_s_tmp_type "100x75x11"))
        (if (= $value "41") (setq taz_s_tmp_type "120x80x8"))
        (if (= $value "42") (setq taz_s_tmp_type "120x80x10"))
        (if (= $value "43") (setq taz_s_tmp_type "120x80x12"))
        (if (= $value "44") (setq taz_s_tmp_type "120x80x14"))
        (if (= $value "45") (setq taz_s_tmp_type "130x65x8"))
        (if (= $value "46") (setq taz_s_tmp_type "130x65x10"))
        (if (= $value "47") (setq taz_s_tmp_type "130x65x12"))
        (if (= $value "48") (setq taz_s_tmp_type "130x90x12"))
        (if (= $value "49") (setq taz_s_tmp_type "150x75x9"))
        (if (= $value "50") (setq taz_s_tmp_type "150x75x11"))
        (if (= $value "51") (setq taz_s_tmp_type "150x100x10"))
        (if (= $value "52") (setq taz_s_tmp_type "150x100x12"))
        (if (= $value "53") (setq taz_s_tmp_type "150x100x14"))
        (if (= $value "54") (setq taz_s_tmp_type "160x80x12"))
        (if (= $value "55") (setq taz_s_tmp_type "180x90x10"))
        (if (= $value "56") (setq taz_s_tmp_type "180x90x12"))
        (if (= $value "57") (setq taz_s_tmp_type "200x100x10"))
        (if (= $value "58") (setq taz_s_tmp_type "200x100x12"))
        (if (= $value "59") (setq taz_s_tmp_type "200x100x14"))
        (if (= $value "60") (setq taz_s_tmp_type "200x100x16"))
        (if (= $value "61") (setq taz_s_tmp_type "250x90x10"))
        (if (= $value "62") (setq taz_s_tmp_type "250x90x12"))
        (if (= $value "63") (setq taz_s_tmp_type "250x90x14"))
        (if (= $value "64") (setq taz_s_tmp_type "250x90x16"))
      )
    )

    ;; Rury - Rura kwadratowa (SHS)
    (if (= taz_s_tmp_family "Rura kwadratowa") 
      (progn 
        (if (= $value "0") (setq taz_s_tmp_type "38x38x2.5"))
        (if (= $value "1") (setq taz_s_tmp_type "38x38x3"))
        (if (= $value "2") (setq taz_s_tmp_type "38x38x3.5"))
        (if (= $value "3") (setq taz_s_tmp_type "50x50x2.5"))
        (if (= $value "4") (setq taz_s_tmp_type "50x50x3"))
        (if (= $value "5") (setq taz_s_tmp_type "50x50x3.5"))
        (if (= $value "6") (setq taz_s_tmp_type "50x50x4"))
        (if (= $value "7") (setq taz_s_tmp_type "50x50x4.5"))
        (if (= $value "8") (setq taz_s_tmp_type "60x60x2.5"))
        (if (= $value "9") (setq taz_s_tmp_type "60x60x3"))
        (if (= $value "10") (setq taz_s_tmp_type "60x60x3.5"))
        (if (= $value "11") (setq taz_s_tmp_type "60x60x4"))
        (if (= $value "12") (setq taz_s_tmp_type "60x60x4.5"))
        (if (= $value "13") (setq taz_s_tmp_type "75x75x2.5"))
        (if (= $value "14") (setq taz_s_tmp_type "75x75x3"))
        (if (= $value "15") (setq taz_s_tmp_type "75x75x3.5"))
        (if (= $value "16") (setq taz_s_tmp_type "75x75x4"))
        (if (= $value "17") (setq taz_s_tmp_type "75x75x4.5"))
        (if (= $value "18") (setq taz_s_tmp_type "75x75x5"))
        (if (= $value "19") (setq taz_s_tmp_type "80x80x2.5"))
        (if (= $value "20") (setq taz_s_tmp_type "80x80x3"))
        (if (= $value "21") (setq taz_s_tmp_type "80x80x3.5"))
        (if (= $value "22") (setq taz_s_tmp_type "80x80x4"))
        (if (= $value "23") (setq taz_s_tmp_type "80x80x4.5"))
        (if (= $value "24") (setq taz_s_tmp_type "80x80x5"))
        (if (= $value "25") (setq taz_s_tmp_type "80x80x6"))
        (if (= $value "26") (setq taz_s_tmp_type "100x100x2.5"))
        (if (= $value "27") (setq taz_s_tmp_type "100x100x3"))
        (if (= $value "28") (setq taz_s_tmp_type "100x100x3.5"))
        (if (= $value "29") (setq taz_s_tmp_type "100x100x4"))
        (if (= $value "30") (setq taz_s_tmp_type "100x100x4.5"))
        (if (= $value "31") (setq taz_s_tmp_type "100x100x5"))
        (if (= $value "32") (setq taz_s_tmp_type "100x100x6"))
        (if (= $value "33") (setq taz_s_tmp_type "120x120x3"))
        (if (= $value "34") (setq taz_s_tmp_type "120x120x3.5"))
        (if (= $value "35") (setq taz_s_tmp_type "120x120x4"))
        (if (= $value "36") (setq taz_s_tmp_type "120x120x4.5"))
        (if (= $value "37") (setq taz_s_tmp_type "120x120x5"))
        (if (= $value "38") (setq taz_s_tmp_type "120x120x6"))
        (if (= $value "39") (setq taz_s_tmp_type "150x150x4"))
        (if (= $value "40") (setq taz_s_tmp_type "150x150x4.5"))
        (if (= $value "41") (setq taz_s_tmp_type "150x150x6"))
        (if (= $value "42") (setq taz_s_tmp_type "150x150x8"))
        (if (= $value "43") (setq taz_s_tmp_type "150x150x10"))
        (if (= $value "44") (setq taz_s_tmp_type "175x175x4"))
        (if (= $value "45") (setq taz_s_tmp_type "175x175x4.5"))
        (if (= $value "46") (setq taz_s_tmp_type "175x175x6"))
        (if (= $value "47") (setq taz_s_tmp_type "175x175x8"))
        (if (= $value "48") (setq taz_s_tmp_type "175x175x10"))
        (if (= $value "49") (setq taz_s_tmp_type "200x200x4.5"))
        (if (= $value "50") (setq taz_s_tmp_type "200x200x6"))
        (if (= $value "51") (setq taz_s_tmp_type "200x200x8"))
        (if (= $value "52") (setq taz_s_tmp_type "200x200x10"))
        (if (= $value "53") (setq taz_s_tmp_type "220x220x6"))
        (if (= $value "54") (setq taz_s_tmp_type "220x220x8"))
        (if (= $value "55") (setq taz_s_tmp_type "220x220x10"))
        (if (= $value "56") (setq taz_s_tmp_type "250x250x4.5"))
        (if (= $value "57") (setq taz_s_tmp_type "250x250x6"))
        (if (= $value "58") (setq taz_s_tmp_type "250x250x8"))
        (if (= $value "59") (setq taz_s_tmp_type "250x250x10"))
        (if (= $value "60") (setq taz_s_tmp_type "285x285x8"))
        (if (= $value "61") (setq taz_s_tmp_type "285x285x10"))
      )
    )

    ;; Rury - Rura prostokatna (RHS)
    (if (= taz_s_tmp_family "Rura prostokatna") 
      (progn 
        (if (= $value "0") (setq taz_s_tmp_type "50x25x2.5"))
        (if (= $value "1") (setq taz_s_tmp_type "50x25x3"))
        (if (= $value "2") (setq taz_s_tmp_type "50x25x3.5"))
        (if (= $value "3") (setq taz_s_tmp_type "60x40x2.5"))
        (if (= $value "4") (setq taz_s_tmp_type "60x40x3"))
        (if (= $value "5") (setq taz_s_tmp_type "60x40x3.5"))
        (if (= $value "6") (setq taz_s_tmp_type "60x40x4"))
        (if (= $value "7") (setq taz_s_tmp_type "60x40x4.5"))
        (if (= $value "8") (setq taz_s_tmp_type "76x38x2.5"))
        (if (= $value "9") (setq taz_s_tmp_type "76x38x3"))
        (if (= $value "10") (setq taz_s_tmp_type "76x38x3.5"))
        (if (= $value "11") (setq taz_s_tmp_type "76x38x4"))
        (if (= $value "12") (setq taz_s_tmp_type "76x38x4.5"))
        (if (= $value "13") (setq taz_s_tmp_type "80x40x2.5"))
        (if (= $value "14") (setq taz_s_tmp_type "80x40x3"))
        (if (= $value "15") (setq taz_s_tmp_type "80x40x3.5"))
        (if (= $value "16") (setq taz_s_tmp_type "80x40x4"))
        (if (= $value "17") (setq taz_s_tmp_type "80x40x4.5"))
        (if (= $value "18") (setq taz_s_tmp_type "100x50x2.5"))
        (if (= $value "19") (setq taz_s_tmp_type "100x50x3"))
        (if (= $value "20") (setq taz_s_tmp_type "100x50x3.5"))
        (if (= $value "21") (setq taz_s_tmp_type "100x50x4"))
        (if (= $value "22") (setq taz_s_tmp_type "100x50x4.5"))
        (if (= $value "23") (setq taz_s_tmp_type "100x50x5"))
        (if (= $value "24") (setq taz_s_tmp_type "100x50x6"))
        (if (= $value "25") (setq taz_s_tmp_type "120x60x3"))
        (if (= $value "26") (setq taz_s_tmp_type "120x60x3.5"))
        (if (= $value "27") (setq taz_s_tmp_type "120x60x4"))
        (if (= $value "28") (setq taz_s_tmp_type "120x60x4.5"))
        (if (= $value "29") (setq taz_s_tmp_type "120x60x5"))
        (if (= $value "30") (setq taz_s_tmp_type "120x60x6"))
        (if (= $value "31") (setq taz_s_tmp_type "150x100x3"))
        (if (= $value "32") (setq taz_s_tmp_type "150x100x3.5"))
        (if (= $value "33") (setq taz_s_tmp_type "150x100x4"))
        (if (= $value "34") (setq taz_s_tmp_type "150x100x4.5"))
        (if (= $value "35") (setq taz_s_tmp_type "150x100x5"))
        (if (= $value "36") (setq taz_s_tmp_type "150x100x6"))
        (if (= $value "37") (setq taz_s_tmp_type "160x80x3"))
        (if (= $value "38") (setq taz_s_tmp_type "160x80x3.5"))
        (if (= $value "39") (setq taz_s_tmp_type "160x80x4"))
        (if (= $value "40") (setq taz_s_tmp_type "160x80x4.5"))
        (if (= $value "41") (setq taz_s_tmp_type "160x80x5"))
        (if (= $value "42") (setq taz_s_tmp_type "160x80x6"))
        (if (= $value "43") (setq taz_s_tmp_type "200x100x4"))
        (if (= $value "44") (setq taz_s_tmp_type "200x100x4.5"))
        (if (= $value "45") (setq taz_s_tmp_type "200x100x6"))
        (if (= $value "46") (setq taz_s_tmp_type "200x100x8"))
        (if (= $value "47") (setq taz_s_tmp_type "200x100x10"))
        (if (= $value "48") (setq taz_s_tmp_type "200x150x4"))
        (if (= $value "49") (setq taz_s_tmp_type "200x150x4.5"))
        (if (= $value "50") (setq taz_s_tmp_type "200x150x6"))
        (if (= $value "51") (setq taz_s_tmp_type "200x150x8"))
        (if (= $value "52") (setq taz_s_tmp_type "200x150x10"))
        (if (= $value "53") (setq taz_s_tmp_type "250x100x4"))
        (if (= $value "54") (setq taz_s_tmp_type "250x100x4.5"))
        (if (= $value "55") (setq taz_s_tmp_type "250x100x6"))
        (if (= $value "56") (setq taz_s_tmp_type "250x100x8"))
        (if (= $value "57") (setq taz_s_tmp_type "250x100x10"))
        (if (= $value "58") (setq taz_s_tmp_type "250x150x6"))
        (if (= $value "59") (setq taz_s_tmp_type "250x150x8"))
        (if (= $value "60") (setq taz_s_tmp_type "250x150x10"))
        (if (= $value "61") (setq taz_s_tmp_type "300x140x6"))
        (if (= $value "62") (setq taz_s_tmp_type "300x140x8"))
        (if (= $value "63") (setq taz_s_tmp_type "300x140x10"))
        (if (= $value "64") (setq taz_s_tmp_type "320x200x6"))
        (if (= $value "65") (setq taz_s_tmp_type "320x200x8"))
        (if (= $value "66") (setq taz_s_tmp_type "320x200x10"))
        (if (= $value "67") (setq taz_s_tmp_type "340x180x6"))
        (if (= $value "68") (setq taz_s_tmp_type "340x180x8"))
        (if (= $value "69") (setq taz_s_tmp_type "340x180x10"))
      )
    )


    ;; Rury - Rura okragla (CHS)
    (if (= taz_s_tmp_family "Rura okragla") 
      (progn 
        (if (= $value "0") (setq taz_s_tmp_type "508x12.7"))
        (if (= $value "1") (setq taz_s_tmp_type "508x9.5"))
        (if (= $value "2") (setq taz_s_tmp_type "457.2x12.7"))
        (if (= $value "3") (setq taz_s_tmp_type "457.2x9.5"))
        (if (= $value "4") (setq taz_s_tmp_type "406.4x12.7"))
        (if (= $value "5") (setq taz_s_tmp_type "406.4x11.1"))
        (if (= $value "6") (setq taz_s_tmp_type "406.4x9.5"))
        (if (= $value "7") (setq taz_s_tmp_type "406.4x7.9"))
        (if (= $value "8") (setq taz_s_tmp_type "355.6x12.7"))
        (if (= $value "9") (setq taz_s_tmp_type "355.6x9.5"))
        (if (= $value "10") (setq taz_s_tmp_type "355.6x7.9"))
        (if (= $value "11") (setq taz_s_tmp_type "323.9x12.7"))
        (if (= $value "12") (setq taz_s_tmp_type "323.9x9.5"))
        (if (= $value "13") (setq taz_s_tmp_type "323.9x6.4"))
        (if (= $value "14") (setq taz_s_tmp_type "317.5x15.9"))
        (if (= $value "15") (setq taz_s_tmp_type "317.5x12.7"))
        (if (= $value "16") (setq taz_s_tmp_type "317.5x9.5"))
        (if (= $value "17") (setq taz_s_tmp_type "317.5x7.9"))
        (if (= $value "18") (setq taz_s_tmp_type "317.5x6.4"))
        (if (= $value "19") (setq taz_s_tmp_type "317.5x4.8"))
        (if (= $value "20") (setq taz_s_tmp_type "312.8x15.9"))
        (if (= $value "21") (setq taz_s_tmp_type "312.8x12.7"))
        (if (= $value "22") (setq taz_s_tmp_type "312.8x9.5"))
        (if (= $value "23") (setq taz_s_tmp_type "312.8x7.9"))
        (if (= $value "24") (setq taz_s_tmp_type "312.8x6.4"))
        (if (= $value "25") (setq taz_s_tmp_type "312.8x4.8"))
        (if (= $value "26") (setq taz_s_tmp_type "311.2x15.9"))
        (if (= $value "27") (setq taz_s_tmp_type "311.2x12.7"))
        (if (= $value "28") (setq taz_s_tmp_type "311.2x9.5"))
        (if (= $value "29") (setq taz_s_tmp_type "311.2x7.9"))
        (if (= $value "30") (setq taz_s_tmp_type "311.2x6.4"))
        (if (= $value "31") (setq taz_s_tmp_type "311.2x4.8"))
        (if (= $value "32") (setq taz_s_tmp_type "285.8x15.9"))
        (if (= $value "33") (setq taz_s_tmp_type "285.8x12.7"))
        (if (= $value "34") (setq taz_s_tmp_type "285.8x9.5"))
        (if (= $value "35") (setq taz_s_tmp_type "285.8x7.9"))
        (if (= $value "36") (setq taz_s_tmp_type "285.8x6.4"))
        (if (= $value "37") (setq taz_s_tmp_type "285.8x4.8"))
        (if (= $value "38") (setq taz_s_tmp_type "273.1x12.7"))
        (if (= $value "39") (setq taz_s_tmp_type "273.1x9.3"))
        (if (= $value "40") (setq taz_s_tmp_type "273.1x6.4"))
        (if (= $value "41") (setq taz_s_tmp_type "254x15.9"))
        (if (= $value "42") (setq taz_s_tmp_type "254x12.7"))
        (if (= $value "43") (setq taz_s_tmp_type "254x9.5"))
        (if (= $value "44") (setq taz_s_tmp_type "254x7.9"))
        (if (= $value "45") (setq taz_s_tmp_type "254x6.4"))
        (if (= $value "46") (setq taz_s_tmp_type "254x4.8"))
        (if (= $value "47") (setq taz_s_tmp_type "244.5x12.7"))
        (if (= $value "48") (setq taz_s_tmp_type "244.5x9.5"))
        (if (= $value "49") (setq taz_s_tmp_type "244.5x7.9"))
        (if (= $value "50") (setq taz_s_tmp_type "244.5x6.4"))
        (if (= $value "51") (setq taz_s_tmp_type "222.3x12.7"))
        (if (= $value "52") (setq taz_s_tmp_type "222.3x9.5"))
        (if (= $value "53") (setq taz_s_tmp_type "222.3x7.9"))
        (if (= $value "54") (setq taz_s_tmp_type "222.3x6.4"))
        (if (= $value "55") (setq taz_s_tmp_type "222.3x4.8"))
        (if (= $value "56") (setq taz_s_tmp_type "219.1x12.7"))
        (if (= $value "57") (setq taz_s_tmp_type "219.1x9.5"))
        (if (= $value "58") (setq taz_s_tmp_type "219.1x8.2"))
        (if (= $value "59") (setq taz_s_tmp_type "219.1x6.4"))
        (if (= $value "60") (setq taz_s_tmp_type "219.1x4.8"))
        (if (= $value "61") (setq taz_s_tmp_type "193.7x9.5"))
        (if (= $value "62") (setq taz_s_tmp_type "193.7x8.3"))
        (if (= $value "63") (setq taz_s_tmp_type "193.7x3.2"))
        (if (= $value "64") (setq taz_s_tmp_type "190.5x12.7"))
        (if (= $value "65") (setq taz_s_tmp_type "190.5x9.5"))
        (if (= $value "66") (setq taz_s_tmp_type "190.5x7.9"))
        (if (= $value "67") (setq taz_s_tmp_type "190.5x6.4"))
        (if (= $value "68") (setq taz_s_tmp_type "190.5x4.8"))
        (if (= $value "69") (setq taz_s_tmp_type "177.8x12.7"))
        (if (= $value "70") (setq taz_s_tmp_type "177.8x9.5"))
        (if (= $value "71") (setq taz_s_tmp_type "177.8x7.9"))
        (if (= $value "72") (setq taz_s_tmp_type "177.8x6.4"))
        (if (= $value "73") (setq taz_s_tmp_type "177.8x4.8"))
        (if (= $value "74") (setq taz_s_tmp_type "177.8x3.2"))
        (if (= $value "75") (setq taz_s_tmp_type "174.6x12.7"))
        (if (= $value "76") (setq taz_s_tmp_type "174.6x9.5"))
        (if (= $value "77") (setq taz_s_tmp_type "174.6x7.9"))
        (if (= $value "78") (setq taz_s_tmp_type "174.6x6.4"))
        (if (= $value "79") (setq taz_s_tmp_type "174.6x4.8"))
        (if (= $value "80") (setq taz_s_tmp_type "168.3x12.7"))
        (if (= $value "81") (setq taz_s_tmp_type "168.3x11"))
        (if (= $value "82") (setq taz_s_tmp_type "168.3x9.5"))
        (if (= $value "83") (setq taz_s_tmp_type "168.3x7.9"))
        (if (= $value "84") (setq taz_s_tmp_type "168.3x7.1"))
        (if (= $value "85") (setq taz_s_tmp_type "168.3x6.4"))
        (if (= $value "86") (setq taz_s_tmp_type "168.3x4.8"))
        (if (= $value "87") (setq taz_s_tmp_type "168.3x3.2"))
        (if (= $value "88") (setq taz_s_tmp_type "155.6x12.7"))
        (if (= $value "89") (setq taz_s_tmp_type "155.6x9.5"))
        (if (= $value "90") (setq taz_s_tmp_type "155.6x7.9"))
        (if (= $value "91") (setq taz_s_tmp_type "155.6x6.4"))
        (if (= $value "92") (setq taz_s_tmp_type "155.6x4.8"))
        (if (= $value "93") (setq taz_s_tmp_type "152.4x12.7"))
        (if (= $value "94") (setq taz_s_tmp_type "152.4x9.5"))
        (if (= $value "95") (setq taz_s_tmp_type "152.4x7.9"))
        (if (= $value "96") (setq taz_s_tmp_type "152.4x7.1"))
        (if (= $value "97") (setq taz_s_tmp_type "152.4x6.4"))
        (if (= $value "98") (setq taz_s_tmp_type "152.4x4.8"))
        (if (= $value "99") (setq taz_s_tmp_type "152.4x3.2"))
        (if (= $value "100") (setq taz_s_tmp_type "141.3x9.5"))
        (if (= $value "101") (setq taz_s_tmp_type "141.3x6.6"))
        (if (= $value "102") (setq taz_s_tmp_type "141.3x4.8"))
        (if (= $value "103") (setq taz_s_tmp_type "141.3x3.4"))
        (if (= $value "104") (setq taz_s_tmp_type "139.7x12.7"))
        (if (= $value "105") (setq taz_s_tmp_type "139.7x9.5"))
        (if (= $value "106") (setq taz_s_tmp_type "139.7x6.6"))
        (if (= $value "107") (setq taz_s_tmp_type "127x12.7"))
        (if (= $value "108") (setq taz_s_tmp_type "127x9.5"))
        (if (= $value "109") (setq taz_s_tmp_type "127x7.9"))
        (if (= $value "110") (setq taz_s_tmp_type "127x6.6"))
        (if (= $value "111") (setq taz_s_tmp_type "127x6.4"))
        (if (= $value "112") (setq taz_s_tmp_type "127x4.8"))
        (if (= $value "113") (setq taz_s_tmp_type "127x3.2"))
        (if (= $value "114") (setq taz_s_tmp_type "114.3x8.6"))
        (if (= $value "115") (setq taz_s_tmp_type "114.3x6"))
        (if (= $value "116") (setq taz_s_tmp_type "114.3x4.8"))
        (if (= $value "117") (setq taz_s_tmp_type "114.3x3.2"))
        (if (= $value "118") (setq taz_s_tmp_type "101.6x8.6"))
        (if (= $value "119") (setq taz_s_tmp_type "101.6x8"))
        (if (= $value "120") (setq taz_s_tmp_type "101.6x6.4"))
        (if (= $value "121") (setq taz_s_tmp_type "101.6x6"))
        (if (= $value "122") (setq taz_s_tmp_type "101.6x5.7"))
        (if (= $value "123") (setq taz_s_tmp_type "101.6x5.6"))
        (if (= $value "124") (setq taz_s_tmp_type "101.6x4.8"))
        (if (= $value "125") (setq taz_s_tmp_type "101.6x3.2"))
        (if (= $value "126") (setq taz_s_tmp_type "88.9x8"))
        (if (= $value "127") (setq taz_s_tmp_type "88.9x7.6"))
        (if (= $value "128") (setq taz_s_tmp_type "88.9x6.4"))
        (if (= $value "129") (setq taz_s_tmp_type "88.9x5.5"))
        (if (= $value "130") (setq taz_s_tmp_type "88.9x5.2"))
        (if (= $value "131") (setq taz_s_tmp_type "88.9x4.8"))
        (if (= $value "132") (setq taz_s_tmp_type "88.9x3.2"))
        (if (= $value "133") (setq taz_s_tmp_type "76.2x7.6"))
        (if (= $value "134") (setq taz_s_tmp_type "76.2x6.4"))
        (if (= $value "135") (setq taz_s_tmp_type "76.2x5.5"))
        (if (= $value "136") (setq taz_s_tmp_type "76.2x5.2"))
        (if (= $value "137") (setq taz_s_tmp_type "76.2x4.8"))
        (if (= $value "138") (setq taz_s_tmp_type "76.2x3.9"))
        (if (= $value "139") (setq taz_s_tmp_type "76.2x3.4"))
        (if (= $value "140") (setq taz_s_tmp_type "76.2x3"))
        (if (= $value "141") (setq taz_s_tmp_type "73x6.4"))
        (if (= $value "142") (setq taz_s_tmp_type "73x5.2"))
        (if (= $value "143") (setq taz_s_tmp_type "73x4.8"))
        (if (= $value "144") (setq taz_s_tmp_type "73x3.2"))
        (if (= $value "145") (setq taz_s_tmp_type "63.5x6.4"))
        (if (= $value "146") (setq taz_s_tmp_type "63.5x4.8"))
        (if (= $value "147") (setq taz_s_tmp_type "63.5x3.2"))
        (if (= $value "148") (setq taz_s_tmp_type "60.3x6.4"))
        (if (= $value "149") (setq taz_s_tmp_type "60.3x5.5"))
        (if (= $value "150") (setq taz_s_tmp_type "60.3x4.8"))
        (if (= $value "151") (setq taz_s_tmp_type "60.3x3.9"))
        (if (= $value "152") (setq taz_s_tmp_type "60.3x3.2"))
        (if (= $value "153") (setq taz_s_tmp_type "48.3x3.7"))
        (if (= $value "154") (setq taz_s_tmp_type "42.2x3.6"))
      )
    )
  )

  (action_tile "taz_s_typ" "(taz_s_on_type_change)")


  ;; ---------------------------
  ;; Przycisk OK
  ;; ---------------------------
  (action_tile "ok" 
               "(progn
       (setq taz_s_category taz_s_tmp_category)
       (setq taz_s_family   taz_s_tmp_family)
       (setq taz_s_type     taz_s_tmp_type)
       (done_dialog 1)
     )"
  )

  ;; ---------------------------
  ;; Przycisk Anuluj
  ;; ---------------------------
  (action_tile "anuluj" 
               "(done_dialog 0)"
  )

  ;; ---------------------------
  ;; Uruchomienie dialogu
  ;; ---------------------------
  (if (= (start_dialog) 1) 
    (progn 
      (princ "\nWybrane wartosci:")
      (princ (strcat "\nKategoria: " taz_s_category))
      (princ (strcat "\nRodzina:   " taz_s_family))
      (princ (strcat "\nTyp:       " taz_s_type))
    )
    (princ "\nAnulowano.")
  )

  (unload_dialog taz_s_dcl_id)
  (princ)
)
